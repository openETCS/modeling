Examples DEFINITIONS ::=
BEGIN
Record-2-elements ::= SEQUENCE {
  a-boolean  BOOLEAN,
  an-integer INTEGER
}

Choice-between-2-elements ::= CHOICE {
  nothing     NULL,
  an-array    SEQUENCE (SIZE (1..100)) OF INTEGER
}

Possible-value ::= ENUMERATED {
  value1, value2, value3
}

List-of-possible-values ::= SEQUENCE OF Possible-value

A-value ::= CHOICE {
  a-limited-integer     INTEGER(0..1023),
  a-limited-real        REAL (WITH COMPONENTS { mantissa (0..100),
                                                base (10),
                                                exponent (-1) })
}

END
