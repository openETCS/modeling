# IBM Rational DOORS, 23 January 2014

# Specification: SUBSET-026_SRS _Ch-2_v330
- ReqIF.Description: SUBSET-026_SRS _Ch-2_v330
- ReqIF.Name: SUBSET-026_SRS _Ch-2_v330

## 287

### 288: 2.1 Modification History

### 289: 2.2 Table of Contents

### 290: 2.3 Introduction

#### 291: 2.3.1 Scope and purpose

##### 292: 2.3.1.1 The present chapter gives the basic description of the ERTMS/ETCS system proposed to achieve technical interoperability.

### 293: 2.4 System structure

#### 294

##### 295: 2.4.1.1 Due to the nature of the required functions, the ERTMS/ETCS system will have to be partly on the trackside and partly on board the trains.

##### 296: 2.4.1.2 This defines two sub-systems, the on-board sub-system and the trackside sub-system.

##### 297: 2.4.1.3 The environment of ERTMS/ETCS system is composed of:

###### 298
the train, which will then be considered in the train interface specification;

###### 299
the driver, which will then be considered via the driver interface specification;

###### 300
other onboard interfaces (see architecture drawing in 2.5.3),

###### 301
external trackside systems (interlockings, control centres, etc.), for which no interoperability requirement will be established.

### 302: 2.5 Sub-systems

#### 303: 2.5.1 Trackside subsystem

##### 304: 2.5.1.1 Depending of the application level (see further sections), the trackside sub-system can be composed of:

###### 305
balise

###### 306
lineside electronic unit

###### 307
the radio communication network (GSM-R)

###### 308
the Radio Block Centre (RBC)

###### 309
Euroloop

###### 310
Radio infill unit

###### 311
Key Management Centre (KMC)

##### 312: 2.5.1.2 Balise

###### 313: 2.5.1.2.1 The balise is a transmission device that can send telegrams to the on-board sub-system.

###### 314: 2.5.1.2.2 The balise is based on the existing Eurobalise specifications. These documents are included in the frame of the ERTMS/ETCS specifications.

###### 315: 2.5.1.2.3 The balises provides the up-link, i. e. the possibility to send messages from trackside to the on-board sub-system.

###### 316: 2.5.1.2.4 The balises can provide fixed messages or, when connected to a lineside electronic unit, messages that can be changed.

###### 317: 2.5.1.2.5 The balises will be organised in groups, each balise transmitting a telegram and the combination of all telegrams defining the message sent by the balise group.

##### 318: 2.5.1.3 Lineside electronic unit

###### 319: 2.5.1.3.1 The lineside electronic units are electronic devices, that generate telegrams to be sent by balises, on basis of information received from external trackside systems.

##### 320: 2.5.1.4 Trackside radio communication network (GSM-R)

###### 321: 2.5.1.4.1 The GSM-R radio communication network is used for the bi-directional exchange of messages between on-board sub-systems and RBC or radio infill units.

###### 322: 2.5.1.4.2 Intentionally deleted

##### 323: 2.5.1.5 RBC

###### 324: 2.5.1.5.1 The RBC is a computer-based system that elaborates messages to be sent to the train on basis of information received from external trackside systems and on basis of information exchanged with the on-board sub-systems.

###### 325: 2.5.1.5.2 The main objective of these messages is to provide movement authorities to allow the safe movement of trains on the Railway infrastructure area under the responsibility of the RBC.

###### 326: 2.5.1.5.3 The interoperability requirements for the RBC are mainly related to the data exchange between the RBC and the on-board sub-system.

##### 327: 2.5.1.6 Euroloop

###### 328: 2.5.1.6.1 The Euroloop subsystem operates on Level 1 lines, providing signalling information in advance as regard to the next main signal in the train running direction.

###### 329: 2.5.1.6.2 The Euroloop subsystem is composed of an on-board functionality and by one or more trackside parts.

##### 330: 2.5.1.7 Radio infill Unit

###### 331: 2.5.1.7.1 The RADIO INFILL subsystem operates on Level 1 lines, providing signalling information in advance as regard to the next main signal in the train running direction.

###### 332: 2.5.1.7.2 The RADIO INFILL subsystem is composed of an on-board functionality and by one or more trackside parts (named RADIO INFILL Unit).

##### 333: 2.5.1.8 KMC

###### 334: 2.5.1.8.1 The role of the KMC is to manage the cryptographic keys, which are used to secure the EURORADIO communications between the ERTMS/ETCS entities (ERTMS/ETCS on-board equipments, RBCs and RIUs).

#### 335: 2.5.2 On-board sub-system

##### 336: 2.5.2.1 Depending of the application level (see further sections), the on-board sub-system can be composed of:

###### 337
the ERTMS/ETCS on-board equipment;

###### 338
the on-board part of the GSM-R radio system;

##### 339: 2.5.2.2 ERTMS/ETCS on-board equipment

###### 340: 2.5.2.2.1 The ERTMS/ETCS on-board equipment is a computer-based system that supervises the movement of the train to which it belongs, on basis of information exchanged with the trackside sub-system.

###### 341: 2.5.2.2.2 The interoperability requirements for the ERTMS/ETCS on-board equipment are related to the functionality and the data exchange between the trackside sub-systems and the on-board sub-system and to the functional data exchange between the on-board sub-system and:

###### 342
the driver;

###### 343
the train;

###### 344
the onboard part of the existing national train control system(s).

##### 345: 2.5.2.3 Onboard radio communication system (GSM-R)

###### 346: 2.5.2.3.1 The GSM-R on-board radio system is used for the bi-directional exchange of messages between on-board sub-system and RBC or radio infill unit.

###### 347: 2.5.2.3.2 Intentionally deleted.

#### 348: 2.5.3 ERTMS/ETCS reference architecture

##### 349
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
##### 350
Figure 1: ERTMS/ETCS system and its interfaces

##### 351: 2.5.3.1 Note: the entities inside the ERTMS/ETCS on-board equipment box are shown only to highlight the scope of the interfaces that are specified in the TSI CCS annex A.

### 352: 2.6 Levels and transitions

#### 353: 2.6.1 Introduction

##### 354: 2.6.1.1 The different ERTMS/ETCS application levels (short: levels) are a way to express the possible operating relationships between track and train. Level definitions are related to the trackside equipment used, to the way trackside information reaches the on-board units and to which functions are processed in the trackside and in the on-board equipment respectively.

##### 355: 2.6.1.2 Different levels have been defined to allow each individual railway administration to select the appropriate ERTMS/ETCS application trackside, according to their strategies, to their trackside infrastructure and to the required performance. Furthermore, the different application levels permit the interfacing of individual signalling systems and train control systems to ERTMS/ETCS.

##### 356: 2.6.1.3 For the purpose of a consistent specification a level 0 has been defined. This level is used for operation on non-equipped (unfitted) lines or on lines equipped with train control system(s) but operation under their supervision is currently not possible.

#### 357: 2.6.2 Definitions

##### 358: 2.6.2.1 A train equipped with ERTMS/ETCS on-board equipment always co-operates with the ERTMS/ETCS trackside equipment in a defined ERTMS/ETCS level.

##### 359: 2.6.2.2 All transitions between levels are performed according to well-specified rules.

##### 360: 2.6.2.3 ERTMS/ETCS can be configured to operate in one of the following application levels:

###### 361
ERTMS/ETCS Level 0 (train equipped with ERTMS/ETCS operating on a line not equipped with any train control system (ERTMS/ETCS or national system) or on a line equipped with ERTMS/ETCS and/or national system(s) but operation under their supervision is currently not possible)

###### 362
ERTMS/ETCS Level NTC (train equipped with ERTMS/ETCS operating on a line equipped with a national system)

###### 363
ERTMS/ETCS Application Level 1 with or without infill transmission (train equipped with ERTMS/ETCS operating on a line equipped with Eurobalises and optionally Euroloop or Radio infill)

###### 364
ERTMS/ETCS Application Level 2 (train equipped with ERTMS/ETCS operating on a line controlled by a Radio Block Centre and equipped with Eurobalises and Euroradio) with train position and train integrity proving performed by the trackside

###### 365
ERTMS/ETCS Application Level 3 (similar to level 2 but with train position and train integrity supervision based on information received from the train)

##### 366: 2.6.2.4 It is possible to superimpose several application levels in parallel on the same track, for example to run trains without train integrity device in level 2 and in parallel trains equipped with train integrity device in level 3. Other examples might be a station which is shared by trains arriving over level 1 and level 2 lines (junctions) or parallel operation of a national system with ERTMS/ETCS. Mixed levels are supported.

##### 367: 2.6.2.5 Levels 1, 2 and 3 are downwards compatible. This means that:

###### 368
- a level 3 equipped train is also able to operate in level 0, level 1 and level 2

###### 369
- a level 2 equipped train is also able to operate in level 0 and level 1

###### 370
- a level 1 equipped train is also able to operate in level 0

##### 371: 2.6.2.6 Note: Operation under level NTC is not part of the downward compatibility chain.

##### 372: 2.6.2.7 It is possible to transmit information not intended for ERTMS/ETCS but for other systems over the ERTMS/ETCS transmission channels. This information is not used by ERTMS/ETCS.

#### 373: 2.6.3 ERTMS/ETCS Application Level 0

##### 374: 2.6.3.1 General description

###### 375: 2.6.3.1.1 Level 0 covers operation of ETCS equipped trains on lines not equipped with ETCS or national systems or on lines where trackside ERTMS/ETCS infrastructure and/or national systems may exist but operation under their supervision is currently not possible (e.g. commissioning or on-board/trackside failed components).

###### 376: 2.6.3.1.2 In Level 0 it is authorized to operate trains without any train control system and therefore line side optical signals or other means of signalling are used to give movement authorities to the driver.

###### 377: 2.6.3.1.3 ERTMS/ETCS on-board equipment provides no supervision except of the maximum design speed of a train and maximum speed permitted in unfitted areas.

###### 378: 2.6.3.1.4 Train detection and train integrity supervision are performed by the trackside equipment of the underlying signalling system (interlocking, track circuits etc.) and are outside the scope of ERTMS/ETCS.

###### 379: 2.6.3.1.5 Level 0 uses no track-train transmission except Eurobalises to announce/command level transitions. Eurobalises therefore still have to be read. No balise data except certain special commands are interpreted.

###### 380: 2.6.3.1.6 No supervisory information is indicated on the DMI except the train speed. Train data has to be entered in order not to have to stop a train at a level transition to ERTMS/ETCS equipped area and to supervise maximum train speed.

###### 381
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
###### 382
Figure 2: ERTMS/ETCS Application Level 0

##### 383: 2.6.3.2 Summary of characteristics of Application Level 0

###### 384: 2.6.3.2.1 Trackside equipment:

###### 385
No ERTMS/ETCS trackside equipment is used except for Eurobalises to announce level transitions and other specific commands.

###### 386: 2.6.3.2.2 Main ERTMS/ETCS trackside functions:

###### 387
None.

###### 388: 2.6.3.2.3 On-board equipment:

###### 389
Onboard equipment with Eurobalise transmission.

###### 390: 2.6.3.2.4 Main ERTMS/ETCS on-board functions:

###### 391
Supervision of maximum train speed.

###### 392
Supervision of maximum speed permitted in an unfitted area.

###### 393
Reading of Eurobalises to detect level transitions and certain special commands. All other messages are rejected.

###### 394
No cab signalling.

#### 395: 2.6.4 ERTMS/ETCS Application Level NTC

##### 396: 2.6.4.1 General description

###### 397: 2.6.4.1.1 Level NTC is used to run ERTMS/ETCS equipped trains on lines equipped with national train control and speed supervision systems.

###### 398: 2.6.4.1.2 Train control information generated trackside by the national train control system is transmitted to the train via the communication channels of the underlying national system.

###### 399: 2.6.4.1.3 Note: Lineside optical signals might be necessary or not, depending on the performance and functionality of the underlying systems.

###### 400: 2.6.4.1.4 Intentionally deleted.

###### 401: 2.6.4.1.5 The achievable level of supervision is similar to the one provided by the underlying national systems.

###### 402: 2.6.4.1.6 Train detection and train integrity supervision are performed by equipment external to ERTMS/ETCS.

###### 403: 2.6.4.1.7 Level NTC uses no ERTMS/ETCS track-train information except to announce/command level transitions and specific commands related to balise transmission. Eurobalises therefore still have to be read.

###### 404: 2.6.4.1.8 The information displayed to the driver depends on the functionality of the underlying national system. The active national system is indicated to the driver as part of that information. Full train data has to be entered in order not to have to stop a train at a level transition position and to supervise maximum train speed.

###### 405: 2.6.4.1.9 A combination of national systems can be regarded as one NTC level.

###### 406: 2.6.4.1.10 Depending on the functionality and the configuration of the specific national system installed onboard, the ERTMS/ETCS Onboard system may need to be interfaced to it, in order to perform the transitions from/to the national system and/or in order to give access to ERTMS/ETCS Onboard resources (e.g. DMI). This can be achieved through a device called an STM (Specific Transmission Module) using a standardised interface.

###### 407: 2.6.4.1.11 Intentionally deleted.

###### 408
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
###### 409
Figure 3: ERTMS/ETCS Application Level NTC

##### 410: 2.6.4.2 Summary of characteristics of Application Level NTC

###### 411: 2.6.4.2.1 Trackside equipment:

###### 412
Level NTC uses the track-train transmission system from an underlying national system, which is not part of ERTMS/ETCS.

###### 413
For level transition purposes Eurobalises are used.

###### 414: 2.6.4.2.2 Main ERTMS/ETCS trackside functions:

###### 415
None.

###### 416: 2.6.4.2.3 On-board equipment:

###### 417
Onboard equipment with Eurobalise transmission.

###### 418
Onboard part of the national system.

###### 419: 2.6.4.2.4 Main ERTMS/ETCS on-board function:

###### 420
No train supervision, it is fully handed over to the national system.

###### 421
Reading of Eurobalises to detect level transitions and certain special commands. All other messages are rejected.

###### 422
Management of the national system through STM, in case the ERTMS/ETCS on-board equipment is interfaced to the national system through an STM.

###### 423
No cab signalling.

#### 424: 2.6.5 ERTMS/ETCS Application Level 1

##### 425: 2.6.5.1 General description

###### 426: 2.6.5.1.1 ERTMS/ETCS Level 1 is a spot transmission based train control system to be used as an overlay on an underlying signalling system.

###### 427: 2.6.5.1.2 Movement authorities are generated trackside and are transmitted to the train via Eurobalises.

###### 428: 2.6.5.1.3 ERTMS/ETCS Level 1 provides a continuous speed supervision system, which also protects against overrun of the authority.

###### 429: 2.6.5.1.4 Train detection and train integrity supervision are performed by the trackside equipment of the underlying signalling system (interlocking, track circuits etc.) and are outside the scope of ERTMS/ETCS.

###### 430: 2.6.5.1.5 Level 1 is based on Eurobalises as spot transmission devices.

###### 431: 2.6.5.1.6 The trackside equipment does not know the train to which it sends information.

###### 432: 2.6.5.1.7 If in level 1 a lineside signal clears, an approaching train can not receive this information until it passes the Eurobalise group at that signal. The driver therefore has to observe the lineside signal to know when to proceed. The train has then to be permitted to approach the stopping location below a maximum permitted release speed.

###### 433: 2.6.5.1.8 Additional Eurobalises can be placed between distant and main signals to transmit infill information, the train will receive new information before reaching the signal.

###### 434: 2.6.5.1.9 Note: Lineside signals are required in level 1 applications, except if semi-continuous infill is provided.

###### 435: 2.6.5.1.10 Semi-continuous infill can be provided using Euroloop or radio infill. In this case, the on-board system will be able to show new information to the driver as soon as it is available and even at standstill.

###### 436: 2.6.5.1.11 Euroloop or radio infill can improve the safety of a level 1 system as they allow the operation without release speed.

###### 437
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
###### 438
Figure 4: ERTMS/ETCS Application Level 1 without infill function

###### 439
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
###### 440
Figure 5: ERTMS/ETCS Application Level 1 with infill function by Euroloop or Radio infill

##### 441: 2.6.5.2 Summary of characteristics of Application Level 1

###### 442: 2.6.5.2.1 Trackside equipment:

###### 443
Eurobalises for spot transmission from track to train.

###### 444
Eurobalises must be able to transmit variable information.

###### 445
Semi continuous infill transmission by using Euroloop or radio infill is optional.

###### 446: 2.6.5.2.2 Main ERTMS/ETCS trackside function:

###### 447
Determine movement authorities according to the underlying signalling system.

###### 448
Transmit movement authorities and track description data to the train.

###### 449: 2.6.5.2.3 On-board equipment:

###### 450
Onboard equipment with Eurobalise transmission.

###### 451
Euroloop transmission if infill by Euroloop is required.

###### 452
- Radio infill transmission if infill by radio is required.

###### 453: 2.6.5.2.4 Main ERTMS/ETCS on-board function:

###### 454
Reception of movement authority and track description related to the transmitting balise.

###### 455
Selection of the most restrictive value of the different speeds permitted at each location ahead.

###### 456
Calculation of a dynamic speed profile taking into account the train running/braking characteristics which are known on-board and the track description data.

###### 457
Comparison of the train speed with the permitted speed and commanding of the brake application if necessary.

###### 458
Cab signalling to the driver.

#### 459: 2.6.6 ERTMS/ETCS Application Level 2

##### 460: 2.6.6.1 General description

###### 461: 2.6.6.1.1 ERTMS/ETCS Level 2 is a radio based train control system which is used as an overlay on an underlying signalling system.

###### 462: 2.6.6.1.2 Movement authorities are generated trackside and are transmitted to the train via Euroradio.

###### 463: 2.6.6.1.3 ERTMS/ETCS Level 2 provides a continuous speed supervision system, which also protects against overrun of the authority.

###### 464: 2.6.6.1.4 Train detection and train integrity supervision are performed by the trackside equipment of the underlying signalling system (interlocking, track circuits etc.) and are outside the scope of ERTMS/ETCS.

###### 465: 2.6.6.1.5 Level 2 is based on Euroradio for track to train communication and on Eurobalises as spot transmission devices mainly for location referencing.

###### 466: 2.6.6.1.6 The trackside radio block centre which provides the information to the trains knows each ERTMS/ETCS controlled train individually by the ERTMS/ETCS identity of its leading ERTMS/ETCS on-board equipment.

###### 467: 2.6.6.1.7 Note: Lineside signals can be suppressed in Level 2.

###### 468
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Figure 6: ERTMS/ETCS Application Level 2

##### 469: 2.6.6.2 Summary of characteristics of Application Level 2

###### 470: 2.6.6.2.1 Trackside equipment:

###### 471
Radio block centre.

###### 472
Euroradio for bi-directional track-train communication.

###### 473
Eurobalises mainly for location referencing.

###### 474: 2.6.6.2.2 Main ERTMS/ETCS trackside function:

###### 475
Knowing each train equipped with and running under ERTMS/ETCS within an RBC area by its ERTMS/ETCS identity.

###### 476
Following each ERTMS/ETCS controlled train’s location within an RBC area.

###### 477
Determine movement authorities according to the underlying signalling system for each train individually.

###### 478
Transmit movement authorities and track description to each train individually.

###### 479
Handing over of train control between different RBC’s at the RBC-RBC borders.

###### 480: 2.6.6.2.3 On-board equipment:

###### 481
Onboard equipment with Eurobalise and Euroradio transmissions.

###### 482: 2.6.6.2.4 Main ERTMS/ETCS on-board function:

###### 483
The train reads Eurobalises and sends its position relative to the detected balises to the radio block centre.

###### 484
The train receives a movement authority and the track description via Euroradio relating to a balise.

###### 485
Selection of the most restrictive value of the different speeds permitted at each location ahead.

###### 486
Calculation of a dynamic speed profile taking into account the train running/braking characteristics which are known on-board and the track description data.

###### 487
Comparison of the train speed with the permitted speed and commanding of the brake application if necessary.

###### 488
Cab signalling to the driver.

#### 489: 2.6.7 ERTMS/ETCS Application Level 3

##### 490: 2.6.7.1 General description

###### 491: 2.6.7.1.1 ERTMS/ETCS Level 3 is a radio based train control system.

###### 492: 2.6.7.1.2 Movement authorities are generated trackside and are transmitted to the train via Euroradio.

###### 493: 2.6.7.1.3 ERTMS/ETCS Level 3 provides a continuous speed supervision system, which also protects against overrun of the authority.

###### 494: 2.6.7.1.4 Train position and train integrity supervision are performed by the trackside radio block centre in co-operation with the train (which sends position reports and train integrity information).

###### 495: 2.6.7.1.5 Level 3 is based on Euroradio for track to train communication and on Eurobalises as spot transmission devices mainly for location referencing.

###### 496: 2.6.7.1.6 The trackside radio block centre which provides the information to the trains knows each train individually by the ERTMS/ETCS identity of its leading ERTMS/ETCS on-board equipment.

###### 497: 2.6.7.1.7 Note: Lineside signals are not foreseen to be used when operating in Level 3.

###### 498
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
###### 499
Figure 7: ERTMS/ETCS Application Level 3

##### 500: 2.6.7.2 Summary of characteristics of Application Level 3

###### 501: 2.6.7.2.1 Trackside equipment:

###### 502
Radio block centre.

###### 503
Euroradio for bi-directional track-train communication.

###### 504
Eurobalises for mainly location referencing.

###### 505: 2.6.7.2.2 Main ERTMS/ETCS trackside function:

###### 506
Knowing each train within an RBC area by its ERTMS/ETCS identity.

###### 507
Following each trains location within an RBC area.

###### 508
Route locking and route releasing based on information received from the trains.

###### 509
Determine movement authorities for each train individually.

###### 510
Transmit movement authorities and track description to each train individually.

###### 511
Handing over of train control between different RBC’s at the RBC-RBC borders.

###### 512: 2.6.7.2.3 On-board equipment:

###### 513
Onboard equipment with Eurobalise and Euroradio transmissions.

###### 514
Train integrity proving system.

###### 515: 2.6.7.2.4 Main ERTMS/ETCS on-board functions:

###### 516
The train reads Eurobalises and sends its position relative to the detected balises to the radio block centre.

###### 517
The train monitors train integrity (external function, not part of ERTMS/ETCS) and sends this information to the radio block centre.

###### 518
The train receives a movement authority and the track description via Euroradio relating to a balise.

###### 519
Selection of the most restrictive value of the different speeds permitted at each location ahead.

###### 520
Calculation of a dynamic speed profile, taking into account the train running/braking characteristics which are known on-board and the track description data.

###### 521
Comparison of the train speed with the permitted speed and commanding of the brake application if necessary.

###### 522
Cab signalling to the driver.

#### 523: 2.6.8 Level transitions

##### 524: 2.6.8.1 An ERTMS/ETCS equipment which is not isolated always operates in one of the above described levels. All transitions between these levels are performed according to defined functions and procedures.

##### 525: 2.6.8.2 Additional national functions and rules which might be used by an individual railway to for example prevent not equipped trains from entering a level 2/3 area are not specified here and have to be implemented outside ERTMS/ETCS.

##### 526: 2.6.8.3 The following table shows all possible transitions (marked with Grey):

###### 527: Tabelle

###### 528: Zeile

###### 529
to
from

###### 530
0

###### 531
NTC

###### 532
1

###### 533
2

###### 534
3

###### 535: Zeile

###### 536
0

###### 537

###### 538

###### 539

###### 540

###### 541

###### 542: Zeile

###### 543
NTC

###### 544

###### 545
a)

###### 546

###### 547

###### 548

###### 549: Zeile

###### 550
1

###### 551

###### 552

###### 553

###### 554

###### 555

###### 556: Zeile

###### 557
2

###### 558

###### 559

###### 560

###### 561
b)

###### 562

###### 563: Zeile

###### 564
3

###### 565

###### 566

###### 567

###### 568

###### 569
b)

###### 570
Table 1: Possible level transitions.

###### 571
Transitions between level NTC and level NTC describe the switching from one national system to another national system.

###### 572
Transitions between level 2 and level 2 respectively between level 3 and level 3 describe the handover between RBC’s.
