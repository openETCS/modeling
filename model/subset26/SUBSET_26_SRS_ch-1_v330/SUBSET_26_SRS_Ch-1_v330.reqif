# IBM Rational DOORS, 23 January 2014

# Specification: SUBSET-026_SRS _Ch-1_v330
- ReqIF.Description: SUBSET-026_SRS _Ch-1_v330
- ReqIF.Name: SUBSET-026_SRS _Ch-1_v330

## 61

### 62: 1.1 Modification History

### 63: 1.2 Table of Contents

### 64: 1.3 Introduction

#### 65

##### 66: 1.3.1.1 Train control is an important part of any railway operations management system. In the past a number of different Automatic Train Control (ATC) systems have evolved in different countries at different times. These systems are incompatible and not interoperable with each other. Only a few of these systems are used in more than one country, and even in those cases there have been differences in detailed development which have resulted in incompatible and not interoperable versions.

##### 67: 1.3.1.2 Many railways anticipate a significant increase in density of train traffic and are rethinking their infrastructure strategy, to accommodate high levels of traffic, in which ATC systems play an important part. Also many railways would like to introduce standardised systems to reduce system costs. In order to establish international standardisation of ATC systems, the following document specifies the European Rail Traffic Management System/European Train Control System (ERTMS/ETCS).

### 68: 1.4 Advantages of an International Interoperable System

#### 69

##### 70: 1.4.1.1 The advantages expected by the railways can be summarised as:

###### 71
Cross border interoperability.

###### 72
Improvement of the safety of national and international train traffic.

###### 73
Improvement of international passengers and freight train traffic management.

###### 74
Shorter headway on heavily trafficked lines, by driving on moving block, enabling exploitation of maximum track capacity.

###### 75
The possibility of step-by-step introduction of the new technology.

###### 76
Enabling Pan-European competition between the manufacturers of ERTMS/ETCS components. Strengthening the position of the European railway industry on the world market.

###### 77
Enabling preconditions for future harmonisation in other areas of rail traffic management.

### 78: 1.5 About this Document

#### 79

##### 80: 1.5.1.1 The purpose of this document is to specify the unified European Train Control System (ETCS) from a technical point of view.

##### 81: 1.5.1.2 Some parts of the system are only specified to allow a migration from existing train control systems to ETCS (e.g. STM’s) over a transition period. They might be removed in a future edition of the standard.

##### 82: 1.5.1.3 To reach technical interoperability it is necessary not only that telegrams are generated and understood according to well specified rules but also that a train respectively trackside equipment reacts in a uniform way to information received. Technical interoperability requires specifications of a detailed level.

##### 83: 1.5.1.4 For operational interoperability it is necessary to add operating rules, engineering standards etc. to the system design. Reaching operational interoperability is outside the scope of the SRS.

### 84: 1.6 How to Read and Use the SRS

#### 85

##### 86: 1.6.1.1 The SRS covers 8 chapters, which are briefly described in the section following this introduction.

##### 87: 1.6.1.2 All readers may need to refer to the Glossary of terms and abbreviations (SUBSET-023).

### 88: 1.7 Mandatory and Optional Requirements

#### 89

##### 90: 1.7.1.1 This specification often offers multiple solutions on how to implement a specific function. It therefore contains both mandatory and optional requirements. Mandatory requirements are always referred to using the word “shall” where else optional requirements are referred to using the word “may”.

##### 91: 1.7.1.2 The ERTMS/ETCS on-board equipment shall implement all mandatory requirements, with the only exceptions and conditions explicitly stated in the Control-Command and Signalling TSI and in this SRS.

##### 92: 1.7.1.3 For ERTMS/ETCS trackside the implementation of functions has to be defined according to the characteristics of the specific lines and the related operational needs. In any case, the requirements of this SRS related to the implemented functions shall be respected.

##### 93: 1.7.1.4 Notes are added to the specification in some parts for clarification. They however never contain requirements.

##### 94: 1.7.1.5 Not specified requirements and solutions are only permitted as long as they do not generate any interoperability problems.

### 95: 1.8 Contents of the SRS

#### 96

##### 97: 1.8.1.1 The SRS defines the system requirements for the European Train Control System (ETCS) of ERTMS..

##### 98: 1.8.1.2 This sub-section is intended to give a rough overview of the contents of each chapter within the SRS so that readers interested only in specialised subjects can easily find the relevant chapters.

#### 99: 1.8.2 Chapter 1: Introduction

##### 100: 1.8.2.1 Chapter 1 (this chapter) gives a general introduction to the intention and structure of the SRS, including a brief overview of the contents of each chapter.

#### 101: 1.8.3 Chapter 2: Basic System Description

##### 102: 1.8.3.1 Chapter 2 gives an overview of the ERTMS/ETCS system structure.

##### 103: 1.8.3.2 Chapter 2 also contains a description of the basic application levels.

##### 104: 1.8.3.3 Chapter 2 does not contain technical requirements.

#### 105: 1.8.4 Chapter 3: Principles

##### 106: 1.8.4.1 Chapter 3 specifies the system principles of ETCS/ERTMS. These principles apply to onboard and trackside subsystems.

##### 107: 1.8.4.2 The principles define the behaviour of the system in general and functional terms.

#### 108: 1.8.5 Chapter 4: Modes and Transitions

##### 109

###### 110: 1.8.5.1.1 Chapter 4 defines the modes of the ERTMS/ETCS onboard equipment and all transitions between modes.

#### 111: 1.8.6 Chapter 5: Procedures

##### 112: 1.8.6.1 Chapter 5 defines the dynamic behaviour of procedures that are necessary for interoperability. Procedures are presented by a state transition chart and a corresponding table, where all elements (States, events, transitions) of the chart are defined. The description of the procedures shows all states of the ERTMS/ETCS onboard unit and the conditions that must be fulfilled to switch from one state to another.

#### 113: 1.8.7 Chapter 6: Management of older System Versions

##### 114

###### 115: 1.8.7.1.1 Chapter 6 defines the envelope of legally operated system versions and lists the exceptions that shall apply by derogation to the requirements listed in the other chapters of the SRS, when an older ERTMS/ETCS system version is used by the trackside subsystem.

#### 116: 1.8.8 Chapter 7: ERTMS/ETCS Language

##### 117: 1.8.8.1 Chapter 7 defines and describes the necessary variables to be used for the data flow over the air gap between track and train. The grouping of these into packets is described. The format of messages is given in Chapter 8.

#### 118: 1.8.9 Chapter 8: Messages

##### 119: 1.8.9.1 Chapter 8 defines the application protocol (format and content of messages, logical sequence for radio) necessary to achieve technical interoperability.

##### 120: 1.8.9.2 The scope of this chapter is limited to the application protocol and the content of messages.
