# Subset026

# Specification: Specification Document
- Description: Subset026

## 2
System Requirements Specification Chapter 2
Basic System Description
- kind: Heading
- WordTraceId: 16
- implement: false
- atomic: true
- Legal Obligation: unknown

### 2.1
Modification History
- kind: ordinary
- WordTraceId: 146
- implement: true
- atomic: false
- Legal Obligation: not applicable

### 2.1[2]
- kind: Placeholder
- WordTraceId: 167
- implement: false
- atomic: false
- Legal Obligation: not applicable

#### 2.1[2].[t]*
| Issue Number Date | Section Number | Modification / Description | Author |
| --- | --- | --- | --- |
| 0.0.1 19 july 1999 | All | First class 1 draft using new templates and including contributions from WPs | PZ |
| 0.1.0 26 july 1999 | System architecture figure § 2.3.1.2 | Updating and introduction of Radio infill Reference to future class 1 deleted | PZ |
| 1.0.0 29 July 1999 | Document version, editorial changes, updating the architecture figure. | Finalisation in Stuttgart 990729 | HE |
| 1.2.0 990730 | Version number | Release version | HE |
| 1.2.1 991209 | All | Draft for 2 nd release | SAB |
| 1.3.0 9912016 | All | Review comments added | SAB |
| 2.0.0 991222 | Minor editing | Finalisation | SAB |
| 2.0.1 | All | Corrections after review | SAB |
| 2.1.0 | Minor editing | UNISIG release | SAB |
| 2.2.0 | Version number | UNISIG release | SAB |
| 2.2.2 1.2.2002 | Version number | Final edition | Ch. Frerichs |
| 2.3.0 24/02/06 | Version number No change since 2.2.2 | Release version | HK |
| 2.3.2 17/03/08 | Including CRs that are in state “Analysis completed” according to ERA CCM | Working version | AH |
| 3.0.0 23/12/08 | Version number No change since 2.3.2 | Release version | AH |
| 3.0.1 22/12/09 |  | Including the results of the editorial review of the SRS 3.0.0 and the other error CR’s that are in state “Analysis completed” according to ERA CCM | AH |
| 3.1.0 22/02/10 |  | Release version | AH |
| 3.1.1 08/11/10 |  | Including all CR’s that are in state “Analysis completed” according to ERA CCM | AH |
| 3.2.0 22/12/10 | No change | Release version | AH |
| 3.2.1 13/12/11 |  | Including all CR’s that are in state “Analysis completed” according to ERA CCM | AH |
| 3.3.0 07/03/12 |  | Baseline 3 release version | AH |
- kind: Table
- WordTraceId: 1713
- implement: false
- atomic: false
- Legal Obligation: not applicable

### 2.2
Table of Contents
- kind: ordinary
- WordTraceId: 1713
- implement: true
- atomic: false
- Legal Obligation: not applicable

### 2.3
Introduction
- kind: Heading
- WordTraceId: 2828
- implement: false
- atomic: false
- Legal Obligation: not applicable

#### 2.3.1
Scope and purpose
- kind: Heading
- WordTraceId: 2841
- implement: false
- atomic: false
- Legal Obligation: not applicable

##### 2.3.1.1
The present chapter gives the basic description of the
ERTMS/ETCS system proposed to achieve technical interoperability.
- kind: ordinary
- WordTraceId: 2859
- implement: true
- atomic: true
- Legal Obligation: unknown

### 2.4
System structure
- kind: Heading
- WordTraceId: 2981
- implement: false
- atomic: false
- Legal Obligation: not applicable

#### 2.4.1
PLACEHOLDER REQUIREMENT - DO NOT TRACE
- kind: Placeholder
- WordTraceId: 2998
- implement: false
- atomic: false
- Legal Obligation: not applicable

##### 2.4.1.1
Due to the nature of the required functions, the
ERTMS/ETCS system
will have to be partly on the trackside and partly on board the trains.
- kind: ordinary
- WordTraceId: 2998
- implementerEnhanced: Due to the nature of the required functions, the ERTMS/ETCS system will have to be partly on the
  trackside
  [EXTERNAL]
  and partly on board the trains.
- implement: true
- atomic: true
- Legal Obligation: unknown

##### 2.4.1.2
This defines two sub-systems, the on-board sub-system and the trackside sub-system.
- kind: Definition
- WordTraceId: 3138
- implementerEnhanced: This defines two sub-systems, the on-board sub-system and the
  trackside
  [EXTERNAL]
  sub-system.
- implement: false
- atomic: true
- Legal Obligation: unknown

##### 2.4.1.3
The environment of ERTMS/ETCS system is composed of:
- kind: Heading
- WordTraceId: 3222
- implement: false
- atomic: true
- Legal Obligation: unknown

###### 2.4.1.3.a
the train, which will then be considered in the train interface specification;
- kind: ordinary
- WordTraceId: 3275
- implement: true
- atomic: true
- Legal Obligation: unknown
- ListNumberText: a)

###### 2.4.1.3.b
the driver, which will then be considered via the driver interface specification;
- kind: ordinary
- WordTraceId: 3354
- implementerEnhanced: the
  driver
  [EXTERNAL]
  , which will then be considered via the
  driver
  [EXTERNAL]
  interface specification;
- implement: true
- atomic: true
- Legal Obligation: unknown
- ListNumberText: b)

###### 2.4.1.3.c
other onboard interfaces (see architecture drawing in 2.5.3),
- kind: ordinary
- WordTraceId: 3436
- implement: true
- atomic: true
- Legal Obligation: unknown
- ListNumberText: c)
- CrossRefLink -> 2.5.3

###### 2.4.1.3.d
external trackside systems (interlockings, control centres, etc.), for which no interoperability requirement will be established.
- kind: ordinary
- WordTraceId: 3498
- implementerEnhanced: external
  [EXTERNAL]
  trackside
  [EXTERNAL]
  systems (interlockings, control centres,
  etc.
  [WEAK]
  ), for which no interoperability requirement will be established.
- implement: true
- atomic: true
- Legal Obligation: unknown
- ListNumberText: d)

### 2.5
Sub-systems
- kind: Heading
- WordTraceId: 3629
- implement: false
- atomic: false
- Legal Obligation: not applicable

#### 2.5.1
Trackside subsystem
- kind: Heading
- WordTraceId: 3641
- implementerEnhanced: Trackside
  [EXTERNAL]
  subsystem
- implement: false
- atomic: false
- Legal Obligation: not applicable

##### 2.5.1.1
Depending of the application level (see further sections), the trackside sub-system can be composed of:
- kind: Heading
- WordTraceId: 3661
- implementerEnhanced: Depending of the application level (see further sections), the
  trackside
  [EXTERNAL]
  sub-system can be composed of:
- implement: false
- atomic: true
- Legal Obligation: unknown

###### 2.5.1.1.a
balise
- kind: ordinary
- WordTraceId: 3765
- implementerEnhanced: balise
  [EXTERNAL]
- implement: true
- atomic: true
- Legal Obligation: unknown
- ListNumberText: a)

###### 2.5.1.1.b
lineside electronic unit
- kind: ordinary
- WordTraceId: 3772
- implementerEnhanced: lineside electronic unit
  [EXTERNAL]
- implement: true
- atomic: true
- Legal Obligation: unknown
- ListNumberText: b)

###### 2.5.1.1.c
the radio communication network (GSM-R)
- kind: ordinary
- WordTraceId: 3797
- implement: true
- atomic: true
- Legal Obligation: unknown
- ListNumberText: c)

###### 2.5.1.1.d
the Radio Block Centre (RBC)
- kind: ordinary
- WordTraceId: 3837
- implementerEnhanced: the
  Radio Block Centre
  [EXTERNAL]
  (
  RBC
  [EXTERNAL]
  )
- implement: true
- atomic: true
- Legal Obligation: unknown
- ListNumberText: d)

###### 2.5.1.1.e
Euroloop
- kind: ordinary
- WordTraceId: 3866
- implementerEnhanced: Euroloop
  [EXTERNAL]
- implement: true
- atomic: true
- Legal Obligation: unknown
- ListNumberText: e)

###### 2.5.1.1.f
Radio infill unit
- kind: ordinary
- WordTraceId: 3875
- implementerEnhanced: Radio infill unit
  [EXTERNAL]
- implement: true
- atomic: true
- Legal Obligation: unknown
- ListNumberText: f)

###### 2.5.1.1.g
Key Management Centre (KMC)
- kind: ordinary
- WordTraceId: 3893
- implement: true
- atomic: true
- Legal Obligation: unknown
- ListNumberText: g)

##### 2.5.1.2
Balise
- kind: Heading
- WordTraceId: 3921
- implementerEnhanced: Balise
  [EXTERNAL]
- implement: false
- atomic: false
- Legal Obligation: not applicable

###### 2.5.1.2.1
The balise is a transmission device that can send telegrams to the on-board sub-system.
- kind: ordinary
- WordTraceId: 3928
- implementerEnhanced: The
  balise
  [EXTERNAL]
  is a transmission device that can send telegrams to the on-board sub-system.
- implement: true
- atomic: true
- Legal Obligation: unknown

###### 2.5.1.2.2
The balise is based on the existing Eurobalise specifications. These documents are included in the frame of the ERTMS/ETCS specifications.
- kind: ordinary
- WordTraceId: 4016
- implementerEnhanced: The
  balise
  [EXTERNAL]
  is based on the existing
  Eurobalise
  [EXTERNAL]
  specifications. These documents are included in the frame of the ERTMS/ETCS specifications.
- implement: true
- atomic: false
- Legal Obligation: unknown

###### 2.5.1.2.3
The balises provides the up-link, i. e. the possibility to send messages from trackside to the on-board sub-system.
- kind: ordinary
- WordTraceId: 4155
- implementerEnhanced: The
  balises
  [EXTERNAL]
  provides the up-link, i. e. the possibility to send messages from
  trackside
  [EXTERNAL]
  to the on-board sub-system.
- implement: true
- atomic: true
- Legal Obligation: unknown

###### 2.5.1.2.4
The balises can provide fixed messages or, when connected to a lineside electronic unit, messages that can be changed.
- kind: ordinary
- WordTraceId: 4271
- implementerEnhanced: The
  balises
  [EXTERNAL]
  can provide fixed messages or,
  when
  [CONDITION]
  connected to a
  lineside electronic unit
  [EXTERNAL]
  , messages that can be changed.
- implement: true
- atomic: true
- Legal Obligation: unknown

###### 2.5.1.2.5
The balises will be organised in groups, each balise transmitting a telegram and the combination of all telegrams defining the message sent by the balise group.
- kind: ordinary
- WordTraceId: 4391
- implementerEnhanced: The
  balises
  [EXTERNAL]
  will be organised in groups, each
  balise
  [EXTERNAL]
  transmitting a telegram and the combination of all telegrams defining the message sent by the
  balise group
  [EXTERNAL]
  .
- implement: true
- atomic: true
- Legal Obligation: unknown

##### 2.5.1.3
Lineside electronic unit
- kind: Heading
- WordTraceId: 4552
- implementerEnhanced: Lineside electronic unit
  [EXTERNAL]
- implement: false
- atomic: false
- Legal Obligation: not applicable

###### 2.5.1.3.1
The lineside electronic units are electronic devices, that generate telegrams to be sent by balises, on basis of information received from external trackside systems.
- kind: ordinary
- WordTraceId: 4577
- implementerEnhanced: The lineside electronic units are electronic devices, that generate telegrams to be sent by
  balises
  [EXTERNAL]
  , on basis of information received from
  external
  [EXTERNAL]
  trackside
  [EXTERNAL]
  systems.
- implement: true
- atomic: true
- Legal Obligation: unknown

##### 2.5.1.4
Trackside radio communication network (GSM-R)
- kind: Heading
- WordTraceId: 4744
- implementerEnhanced: Trackside
  [EXTERNAL]
  radio communication network (GSM-R)
- implement: false
- atomic: false
- Legal Obligation: not applicable

###### 2.5.1.4.1
The GSM-R radio communication network is used for the bi-directional exchange of messages between on-board sub-systems and RBC or radio infill units.
- kind: ordinary
- WordTraceId: 4790
- implementerEnhanced: The GSM-R radio communication network is used for the bi-directional exchange of messages between on-board sub-systems and
  RBC
  [EXTERNAL]
  or radio infill units.
- implement: true
- atomic: true
- Legal Obligation: unknown

###### 2.5.1.4.2
Intentionally deleted
- kind: Placeholder
- WordTraceId: 4941
- implement: false
- atomic: false
- Legal Obligation: not applicable

##### 2.5.1.5
RBC
- kind: Heading
- WordTraceId: 4963
- implementerEnhanced: RBC
  [EXTERNAL]
- implement: false
- atomic: false
- Legal Obligation: not applicable

###### 2.5.1.5.1
The RBC is a computer-based system that elaborates messages to be sent to the train on basis of information received from external trackside systems and on basis of information exchanged with the on-board sub-systems.
- kind: ordinary
- WordTraceId: 4967
- implementerEnhanced: The
  RBC
  [EXTERNAL]
  is a computer-based system that elaborates messages to be sent to the train on basis of information received from
  external
  [EXTERNAL]
  trackside
  [EXTERNAL]
  systems and on basis of information exchanged with the on-board sub-systems.
- implement: true
- atomic: true
- Legal Obligation: unknown

###### 2.5.1.5.2
The main objective of these messages is to provide movement authorities to allow the safe movement of trains on the Railway infrastructure area under the responsibility of the RBC.
- kind: ordinary
- WordTraceId: 5186
- implementerEnhanced: The main objective of these messages is to provide movement authorities to allow the safe movement of trains on the Railway infrastructure area under the responsibility of the
  RBC
  [EXTERNAL]
  .
- implement: true
- atomic: true
- Legal Obligation: unknown

###### 2.5.1.5.3
The interoperability requirements for the RBC are mainly related to the data exchange between the RBC and the on-board sub-system.
- kind: ordinary
- WordTraceId: 5367
- implementerEnhanced: The interoperability requirements for the
  RBC
  [EXTERNAL]
  are mainly related to the data exchange between the
  RBC
  [EXTERNAL]
  and the on-board sub-system.
- implement: true
- atomic: true
- Legal Obligation: unknown

##### 2.5.1.6
Euroloop
- kind: Heading
- WordTraceId: 5498
- implementerEnhanced: Euroloop
  [EXTERNAL]
- implement: false
- atomic: false
- Legal Obligation: not applicable

###### 2.5.1.6.1
The Euroloop subsystem operates on Level 1 lines, providing signalling information in advance as regard to the next main signal in the train running direction.
- kind: ordinary
- WordTraceId: 5507
- implementerEnhanced: The
  Euroloop
  [EXTERNAL]
  subsystem operates on Level 1 lines, providing signalling information in advance as regard to the next main signal in the train running direction.
- implement: true
- atomic: true
- Legal Obligation: unknown

###### 2.5.1.6.2
The Euroloop subsystem is composed of an on-board functionality and by one or more trackside parts.
- kind: ordinary
- WordTraceId: 5667
- implementerEnhanced: The
  Euroloop
  [EXTERNAL]
  subsystem is composed of an on-board functionality and by one or more
  trackside
  [EXTERNAL]
  parts.
- implement: true
- atomic: true
- Legal Obligation: unknown

##### 2.5.1.7
Radio infill Unit
- kind: Heading
- WordTraceId: 5768
- implementerEnhanced: Radio infill Unit
  [EXTERNAL]
- implement: false
- atomic: false
- Legal Obligation: not applicable

###### 2.5.1.7.1
The RADIO INFILL subsystem operates on Level 1 lines, providing signalling information in advance as regard to the next main signal in the train running direction.
- kind: ordinary
- WordTraceId: 5786
- implement: true
- atomic: true
- Legal Obligation: unknown

###### 2.5.1.7.2
The RADIO INFILL subsystem is composed of an on-board functionality and by one or more trackside parts (named RADIO INFILL Unit).
- kind: ordinary
- WordTraceId: 5950
- implementerEnhanced: The RADIO INFILL subsystem is composed of an on-board functionality and by one or more
  trackside
  [EXTERNAL]
  parts (named
  RADIO INFILL Unit
  [EXTERNAL]
  ).
- implement: true
- atomic: true
- Legal Obligation: unknown

##### 2.5.1.8
KMC
- kind: Heading
- WordTraceId: 6081
- implement: false
- atomic: false
- Legal Obligation: not applicable

###### 2.5.1.8.1
The role of the KMC is to manage the cryptographic keys, which are used to secure the EURORADIO communications between the ERTMS/ETCS entities (ERTMS/ETCS on-board equipments, RBCs and RIUs).
- kind: ordinary
- WordTraceId: 6085
- implementerEnhanced: The role of the KMC is to manage the cryptographic keys, which are used to secure the EURORADIO communications between the ERTMS/ETCS entities (
  ERTMS/ETCS on-board
  [SELF]
  equipments, RBCs and RIUs).
- implement: true
- atomic: true
- Legal Obligation: unknown

#### 2.5.2
On-board sub-system
- kind: Heading
- WordTraceId: 6277
- implement: false
- atomic: false
- Legal Obligation: not applicable

##### 2.5.2.1
Depending of the application level (see further sections), the on-board sub-system can be composed of:
- kind: Heading
- WordTraceId: 6297
- implement: false
- atomic: true
- Legal Obligation: unknown

###### 2.5.2.1.a
the ERTMS/ETCS on-board equipment;
- kind: ordinary
- WordTraceId: 6400
- implementerEnhanced: the
  ERTMS/ETCS on-board equipment
  [SELF]
  ;
- implement: true
- atomic: true
- Legal Obligation: unknown
- ListNumberText: a)

###### 2.5.2.1.b
the on-board part of the GSM-R radio system;
- kind: ordinary
- WordTraceId: 6435
- implement: true
- atomic: true
- Legal Obligation: unknown
- ListNumberText: b)

##### 2.5.2.2
ERTMS/ETCS on-board equipment
- kind: Heading
- WordTraceId: 6481
- implementerEnhanced: ERTMS/ETCS on-board equipment
  [SELF]
- implement: false
- atomic: false
- Legal Obligation: not applicable

###### 2.5.2.2.1
The ERTMS/ETCS on-board equipment is a computer-based system that supervises the movement of the train to which it belongs, on basis of information exchanged with the trackside sub-system.
- kind: ordinary
- WordTraceId: 6511
- implementerEnhanced: The
  ERTMS/ETCS on-board equipment
  [SELF]
  is a computer-based system that supervises the movement of the train to which it belongs, on basis of information exchanged with the
  trackside
  [EXTERNAL]
  sub-system.
- implement: true
- atomic: true
- Legal Obligation: unknown

###### 2.5.2.2.2
The interoperability requirements for the ERTMS/ETCS on-board equipment are related to the functionality and the data exchange between the trackside sub-systems and the on-board sub-system and to the functional data exchange between the on-board sub-system and:
- kind: Heading
- WordTraceId: 6701
- implementerEnhanced: The interoperability requirements for the
  ERTMS/ETCS on-board equipment
  [SELF]
  are related to the functionality and the data exchange between the
  trackside
  [EXTERNAL]
  sub-systems and the on-board sub-system and to the functional data exchange between the on-board sub-system and:
- implement: false
- atomic: true
- Legal Obligation: unknown

###### 2.5.2.2.2.a
the driver;
- kind: ordinary
- WordTraceId: 6963
- implementerEnhanced: the
  driver
  [EXTERNAL]
  ;
- implement: true
- atomic: true
- Legal Obligation: unknown
- ListNumberText: a)

###### 2.5.2.2.2.b
the train;
- kind: ordinary
- WordTraceId: 6975
- implement: true
- atomic: true
- Legal Obligation: unknown
- ListNumberText: b)

###### 2.5.2.2.2.c
the onboard part of the existing national train control system(s).
- kind: ordinary
- WordTraceId: 6986
- implement: true
- atomic: true
- Legal Obligation: unknown
- ListNumberText: c)

##### 2.5.2.3
Onboard radio communication system (GSM-R)
- kind: Heading
- WordTraceId: 7053
- implement: false
- atomic: false
- Legal Obligation: not applicable

###### 2.5.2.3.1
The GSM-R on-board radio system is used for the bi-directional exchange of messages between on-board sub-system and RBC or radio infill unit.
- kind: ordinary
- WordTraceId: 7096
- implementerEnhanced: The GSM-R on-board radio system is used for the bi-directional exchange of messages between on-board sub-system and
  RBC
  [EXTERNAL]
  or
  radio infill unit
  [EXTERNAL]
  .
- implement: true
- atomic: true
- Legal Obligation: unknown

###### 2.5.2.3.2
Intentionally deleted.
- kind: Placeholder
- WordTraceId: 7239
- implement: false
- atomic: false
- Legal Obligation: not applicable

#### 2.5.3
ERTMS/ETCS reference architecture
- kind: ordinary
- WordTraceId: 7262
- implement: true
- atomic: false
- Legal Obligation: not applicable

#### 2.5.3[2]
- kind: Placeholder
- WordTraceId: 7297
- implement: false
- atomic: false
- Legal Obligation: not applicable

##### 2.5.3[2].[f]1
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- kind: Figure
- WordTraceId: 7327
- implement: false
- atomic: false
- Legal Obligation: not applicable

###### 2.5.3[2].[f]1.C
Figure {Figure 1}: ERTMS/ETCS system and its interfaces
- kind: Figure
- WordTraceId: 7327
- implementerEnhanced: Figure 1: ERTMS/ETCS system and its interfaces
- implement: false
- atomic: true
- Legal Obligation: unknown

##### 2.5.3[2].1
Note: the entities inside the ERTMS/ETCS on-board equipment box are shown only to highlight the scope of the interfaces that are specified in the TSI CCS annex A.
- kind: Note
- WordTraceId: 7399
- implementerEnhanced: Note: the entities inside the
  ERTMS/ETCS on-board equipment
  [SELF]
  box are shown only to highlight the scope of the interfaces that are specified in the TSI CCS annex A.
- implement: false
- atomic: false
- Legal Obligation: not applicable
- ListNumberText: 2.5.3.1

### 2.6
Levels and transitions
- kind: Heading
- WordTraceId: 7563
- implement: false
- atomic: false
- Legal Obligation: not applicable

#### 2.6.1
Introduction
- kind: Heading
- WordTraceId: 7586
- implement: false
- atomic: false
- Legal Obligation: not applicable

##### 2.6.1.1
The different ERTMS/ETCS application levels (short: levels) are a way to express the possible operating relationships between track and train. Level definitions are related to the trackside equipment used, to the way trackside information reaches the on-board units and to which functions are processed in the trackside and in the on-board equipment respectively.
- kind: ordinary
- WordTraceId: 7599
- implementerEnhanced: The different ERTMS/ETCS application levels (short: levels) are a way to express the possible operating relationships between track and train. Level definitions are related to the
  trackside
  [EXTERNAL]
  equipment used, to the way
  trackside
  [EXTERNAL]
  information reaches the on-board units and to which functions are processed in the
  trackside
  [EXTERNAL]
  and in the
  on-board equipment
  [SELF]
  respectively.
- implement: true
- atomic: false
- Legal Obligation: unknown

##### 2.6.1.2
Different levels have been defined to allow each individual railway administration to select the appropriate ERTMS/ETCS application trackside, according to their strategies, to their trackside infrastructure and to the required performance. Furthermore, the different application levels permit the interfacing of individual signalling systems and train control systems to ERTMS/ETCS.
- kind: ordinary
- WordTraceId: 7964
- implementerEnhanced: Different levels have been defined to allow each individual railway administration to select the appropriate ERTMS/ETCS application
  trackside
  [EXTERNAL]
  , according to their strategies, to their
  trackside
  [EXTERNAL]
  infrastructure and to the required performance. Furthermore, the different application levels permit the interfacing of individual signalling systems and train control systems to ERTMS/ETCS.
- implement: true
- atomic: false
- Legal Obligation: unknown

##### 2.6.1.3
For the purpose of a consistent specification a level 0 has been defined. This level is used for operation on non-equipped (unfitted) lines or on lines equipped with train control system(s) but operation under their supervision is currently not possible.
- kind: ordinary
- WordTraceId: 8348
- implement: true
- atomic: false
- Legal Obligation: unknown

#### 2.6.2
Definitions
- kind: Heading
- WordTraceId: 8604
- implement: false
- atomic: false
- Legal Obligation: not applicable

##### 2.6.2.1
A train equipped with ERTMS/ETCS on-board equipment always co-operates with the ERTMS/ETCS trackside equipment in a defined ERTMS/ETCS level.
- kind: ordinary
- WordTraceId: 8616
- implementerEnhanced: A train equipped with
  ERTMS/ETCS on-board equipment
  [SELF]
  always co-operates with the ERTMS/ETCS
  trackside
  [EXTERNAL]
  equipment in a defined ERTMS/ETCS level.
- implement: true
- atomic: true
- Legal Obligation: unknown

##### 2.6.2.2
All transitions between levels are performed according to well-specified rules.
- kind: ordinary
- WordTraceId: 8759
- implement: true
- atomic: true
- Legal Obligation: unknown

##### 2.6.2.3
ERTMS/ETCS can be configured to operate in one of the following application levels:
- kind: Heading
- WordTraceId: 8840
- implement: false
- atomic: true
- Legal Obligation: unknown

###### 2.6.2.3.*[1]
ERTMS/ETCS Level 0 (train equipped with ERTMS/ETCS operating on a line not equipped with any train control system (ERTMS/ETCS or national system) or on a line equipped with ERTMS/ETCS and/or national system(s) but operation under their supervision is currently not possible)
- kind: ordinary
- WordTraceId: 8925
- implementerEnhanced: ERTMS/ETCS Level 0 (train equipped with ERTMS/ETCS operating on a line not equipped with any train control system (ERTMS/ETCS or
  national system
  [EXTERNAL]
  ) or on a line equipped with ERTMS/ETCS and/or national system(s) but operation under their supervision is currently not possible)
- implement: true
- atomic: true
- Legal Obligation: unknown
- ListNumberText: ·

###### 2.6.2.3.*[2]
ERTMS/ETCS Level NTC (train equipped with ERTMS/ETCS operating on a line equipped with a national system)
- kind: ordinary
- WordTraceId: 9200
- implementerEnhanced: ERTMS/ETCS Level NTC (train equipped with ERTMS/ETCS operating on a line equipped with a
  national system
  [EXTERNAL]
  )
- implement: true
- atomic: true
- Legal Obligation: unknown
- ListNumberText: ·

###### 2.6.2.3.*[3]
ERTMS/ETCS Application Level 1 with or without infill transmission (train equipped with ERTMS/ETCS operating on a line equipped with Eurobalises and optionally Euroloop or Radio infill)
- kind: ordinary
- WordTraceId: 9306
- implementerEnhanced: ERTMS/ETCS Application Level 1 with or without infill transmission (train equipped with ERTMS/ETCS operating on a line equipped with
  Eurobalises
  [EXTERNAL]
  and optionally
  Euroloop
  [EXTERNAL]
  or Radio infill)
- implement: true
- atomic: true
- Legal Obligation: unknown
- ListNumberText: ·

###### 2.6.2.3.*[4]
ERTMS/ETCS Application Level 2 (train equipped with ERTMS/ETCS operating on a line controlled by a Radio Block Centre and equipped with Eurobalises and Euroradio) with train position and train integrity proving performed by the trackside
- kind: ordinary
- WordTraceId: 9492
- implementerEnhanced: ERTMS/ETCS Application Level 2 (train equipped with ERTMS/ETCS operating on a line controlled by a
  Radio Block Centre
  [EXTERNAL]
  and equipped with
  Eurobalises
  [EXTERNAL]
  and Euroradio) with train position and train integrity proving performed by the
  trackside
  [EXTERNAL]
- implement: true
- atomic: true
- Legal Obligation: unknown
- ListNumberText: ·

###### 2.6.2.3.*[5]
ERTMS/ETCS Application Level 3 (similar to level 2 but with train position and train integrity supervision based on information received from the train)
- kind: ordinary
- WordTraceId: 9730
- implement: true
- atomic: true
- Legal Obligation: unknown
- ListNumberText: ·

##### 2.6.2.4
It is possible to superimpose several application levels in parallel on the same track, for example to run trains without train integrity device in level 2 and in parallel trains equipped with train integrity device in level 3. Other examples might be a station which is shared by trains arriving over level 1 and level 2 lines (junctions) or parallel operation of a national system with ERTMS/ETCS. Mixed levels are supported.
- kind: ordinary
- WordTraceId: 9884
- implementerEnhanced: It is possible to superimpose several application levels in parallel on the same track,
  for example
  [WEAK]
  to run trains without train integrity device in level 2 and in parallel trains equipped with train integrity device in level 3. Other examples might be a station which is shared by trains arriving over level 1 and level 2 lines (junctions) or parallel operation of a
  national system
  [EXTERNAL]
  with ERTMS/ETCS. Mixed levels are supported.
- implement: true
- atomic: false
- Legal Obligation: unknown

##### 2.6.2.5
Levels 1, 2 and 3 are downwards compatible. This means that:
- kind: ordinary
- WordTraceId: 10312
- implement: true
- atomic: false
- Legal Obligation: unknown

###### 2.6.2.5.*[1]
a level 3 equipped train is also able to operate in level 0, level 1 and level 2
- kind: ordinary
- WordTraceId: 10373
- implement: true
- atomic: true
- Legal Obligation: unknown
- ListNumberText: ·

###### 2.6.2.5.*[2]
a level 2 equipped train is also able to operate in level 0 and level 1
- kind: ordinary
- WordTraceId: 10454
- implement: true
- atomic: true
- Legal Obligation: unknown
- ListNumberText: ·

###### 2.6.2.5.*[3]
a level 1 equipped train is also able to operate in level 0
- kind: ordinary
- WordTraceId: 10526
- implement: true
- atomic: true
- Legal Obligation: unknown
- ListNumberText: ·

##### 2.6.2.6
Note: Operation under level NTC is not part of the downward compatibility chain.
- kind: Note
- WordTraceId: 10587
- implement: false
- atomic: false
- Legal Obligation: not applicable

##### 2.6.2.7
It is possible to transmit information not intended for ERTMS/ETCS but for other systems over the ERTMS/ETCS transmission channels. This information is not used by ERTMS/ETCS.
- kind: ordinary
- WordTraceId: 10668
- implement: true
- atomic: false
- Legal Obligation: unknown

#### 2.6.3
ERTMS/ETCS Application Level 0
- kind: Heading
- WordTraceId: 10845
- implement: false
- atomic: false
- Legal Obligation: not applicable

##### 2.6.3.1
General description
- kind: Heading
- WordTraceId: 10876
- implement: false
- atomic: false
- Legal Obligation: not applicable

###### 2.6.3.1.1
Level 0 covers operation of ETCS equipped trains on lines not equipped with ETCS or national systems or on lines where trackside ERTMS/ETCS infrastructure and/or national systems may exist but operation under their supervision is currently not possible (e.g. commissioning or on-board/trackside failed components).
- kind: ordinary
- WordTraceId: 10896
- implementerEnhanced: Level 0 covers operation of ETCS equipped trains on lines not equipped with ETCS or national systems or on lines where
  trackside
  [EXTERNAL]
  ERTMS/ETCS infrastructure and/or national systems may exist but operation under their supervision is currently not possible (
  e.g.
  [WEAK]
  commissioning or on-board/
  trackside
  [EXTERNAL]
  failed components).
- implement: true
- atomic: true
- Legal Obligation: optional

###### 2.6.3.1.2
In Level 0 it is authorized to operate trains without any train control system and therefore line side optical signals or other means of signalling are used to give movement authorities to the driver.
- kind: ordinary
- WordTraceId: 11212
- implementerEnhanced: In Level 0 it is authorized to operate trains without any train control system and therefore line side optical signals or other means of signalling are used to give movement authorities to the
  driver
  [EXTERNAL]
  .
- implement: true
- atomic: true
- Legal Obligation: unknown

###### 2.6.3.1.3
ERTMS/ETCS on-board equipment provides no supervision except of the maximum design speed of a train and maximum speed permitted in unfitted areas.
- kind: ordinary
- WordTraceId: 11414
- implementerEnhanced: ERTMS/ETCS on-board equipment
  [SELF]
  provides no supervision except of the maximum design speed of a train and maximum speed permitted in unfitted areas.
- implement: true
- atomic: true
- Legal Obligation: unknown

###### 2.6.3.1.4
Train detection and train integrity supervision are performed by the trackside equipment of the underlying signalling system (interlocking, track circuits etc.) and are outside the scope of ERTMS/ETCS.
- kind: ordinary
- WordTraceId: 11562
- implementerEnhanced: Train detection and train integrity supervision are performed by the
  trackside
  [EXTERNAL]
  equipment of the underlying signalling system (interlocking, track circuits
  etc.
  [WEAK]
  ) and are outside the scope of ERTMS/ETCS.
- implement: true
- atomic: true
- Legal Obligation: unknown

###### 2.6.3.1.5
Level 0 uses no track-train transmission except Eurobalises to announce/command level transitions. Eurobalises therefore still have to be read. No balise data except certain special commands are interpreted.
- kind: ordinary
- WordTraceId: 11764
- implementerEnhanced: Level 0 uses no track-train transmission except
  Eurobalises
  [EXTERNAL]
  to announce/command level transitions.
  Eurobalises
  [EXTERNAL]
  therefore still have to be read. No
  balise
  [EXTERNAL]
  data except certain special commands are interpreted.
- implement: true
- atomic: false
- Legal Obligation: unknown

###### 2.6.3.1.6
No supervisory information is indicated on the DMI except the train speed. Train data has to be entered in order not to have to stop a train at a level transition to ERTMS/ETCS equipped area and to supervise maximum train speed.
- kind: ordinary
- WordTraceId: 11972
- implement: true
- atomic: false
- Legal Obligation: unknown

###### 2.6.3.1.6[2]
- kind: Placeholder
- WordTraceId: 12201
- implement: false
- atomic: false
- Legal Obligation: not applicable

###### 2.6.3.1.6[2].[f]2
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- kind: Figure
- WordTraceId: 12203
- implement: false
- atomic: false
- Legal Obligation: not applicable

###### 2.6.3.1.6[2].[f]2.C
Figure {Figure 2}: ERTMS/ETCS Application Level 0
- kind: Figure
- WordTraceId: 12203
- implementerEnhanced: Figure 2: ERTMS/ETCS Application Level 0
- implement: false
- PlainText: Figure 2: ERTMS/ETCS Application Level 0
- atomic: true
- Legal Obligation: unknown

##### 2.6.3.2
Summary of characteristics of Application Level 0
- kind: Heading
- WordTraceId: 12269
- implement: false
- atomic: false
- Legal Obligation: not applicable

###### 2.6.3.2.1
Trackside equipment:
- kind: Heading
- WordTraceId: 12319
- implementerEnhanced: Trackside
  [EXTERNAL]
  equipment:
- implement: false
- atomic: true
- Legal Obligation: unknown

###### 2.6.3.2.1.*[1]
No ERTMS/ETCS trackside equipment is used except for Eurobalises to announce level transitions and other specific commands.
- kind: ordinary
- WordTraceId: 12341
- implementerEnhanced: No ERTMS/ETCS
  trackside
  [EXTERNAL]
  equipment is used except for
  Eurobalises
  [EXTERNAL]
  to announce level transitions and other specific commands.
- implement: true
- atomic: true
- Legal Obligation: unknown
- ListNumberText: ·

###### 2.6.3.2.2
Main ERTMS/ETCS trackside functions:
- kind: Heading
- WordTraceId: 12465
- implementerEnhanced: Main ERTMS/ETCS
  trackside
  [EXTERNAL]
  functions:
- implement: false
- atomic: true
- Legal Obligation: unknown

###### 2.6.3.2.2.*[1]
None.
- kind: ordinary
- WordTraceId: 12502
- implement: true
- atomic: true
- Legal Obligation: unknown
- ListNumberText: ·

###### 2.6.3.2.3
On-board equipment:
- kind: Heading
- WordTraceId: 12508
- implementerEnhanced: On-board equipment
  [SELF]
  :
- implement: false
- atomic: true
- Legal Obligation: unknown

###### 2.6.3.2.3.*[1]
Onboard equipment with Eurobalise transmission.
- kind: ordinary
- WordTraceId: 12528
- implementerEnhanced: Onboard equipment
  [SELF]
  with
  Eurobalise
  [EXTERNAL]
  transmission.
- implement: true
- atomic: true
- Legal Obligation: unknown
- ListNumberText: ·

###### 2.6.3.2.4
Main ERTMS/ETCS on-board functions:
- kind: Heading
- WordTraceId: 12576
- implementerEnhanced: Main
  ERTMS/ETCS on-board
  [SELF]
  functions:
- implement: false
- atomic: true
- Legal Obligation: unknown

###### 2.6.3.2.4.*[1]
Supervision of maximum train speed.
- kind: ordinary
- WordTraceId: 12612
- implement: true
- atomic: true
- Legal Obligation: unknown
- ListNumberText: ·

###### 2.6.3.2.4.*[2]
Supervision of maximum speed permitted in an unfitted area.
- kind: ordinary
- WordTraceId: 12648
- implement: true
- atomic: true
- Legal Obligation: unknown
- ListNumberText: ·

###### 2.6.3.2.4.*[3]
Reading of Eurobalises to detect level transitions and certain special commands. All other messages are rejected.
- kind: ordinary
- WordTraceId: 12708
- implementerEnhanced: Reading of
  Eurobalises
  [EXTERNAL]
  to detect level transitions and certain special commands. All other messages are rejected.
- implement: true
- atomic: false
- Legal Obligation: unknown
- ListNumberText: ·

###### 2.6.3.2.4.*[4]
No cab signalling.
- kind: ordinary
- WordTraceId: 12822
- implement: true
- atomic: true
- Legal Obligation: unknown
- ListNumberText: ·

#### 2.6.4
ERTMS/ETCS Application Level NTC
- kind: Heading
- WordTraceId: 12842
- implement: false
- atomic: false
- Legal Obligation: not applicable

##### 2.6.4.1
General description
- kind: Heading
- WordTraceId: 12875
- implement: false
- atomic: false
- Legal Obligation: not applicable

###### 2.6.4.1.1
Level NTC is used to run ERTMS/ETCS equipped trains on lines equipped with national train control and speed supervision systems.
- kind: ordinary
- WordTraceId: 12895
- implement: true
- atomic: true
- Legal Obligation: unknown

###### 2.6.4.1.2
Train control information generated trackside by the national train control system is transmitted to the train via the communication channels of the underlying national system.
- kind: ordinary
- WordTraceId: 13025
- implementerEnhanced: Train control information generated
  trackside
  [EXTERNAL]
  by the national train control system is transmitted to the train via the communication channels of the underlying
  national system
  [EXTERNAL]
  .
- implement: true
- atomic: true
- Legal Obligation: unknown

###### 2.6.4.1.3
Note: Lineside optical signals might be necessary or not, depending on the performance and functionality of the underlying systems.
- kind: Note
- WordTraceId: 13203
- implement: false
- atomic: false
- Legal Obligation: not applicable

###### 2.6.4.1.4
Intentionally deleted.
- kind: Placeholder
- WordTraceId: 13336
- implement: false
- atomic: false
- Legal Obligation: not applicable

###### 2.6.4.1.5
The achievable level of supervision is similar to the one provided by the underlying national systems.
- kind: ordinary
- WordTraceId: 13360
- implement: true
- atomic: true
- Legal Obligation: unknown

###### 2.6.4.1.6
Train detection and train integrity supervision are performed by equipment external to ERTMS/ETCS.
- kind: ordinary
- WordTraceId: 13464
- implementerEnhanced: Train detection and train integrity supervision are performed by equipment
  external
  [EXTERNAL]
  to ERTMS/ETCS.
- implement: true
- atomic: true
- Legal Obligation: unknown

###### 2.6.4.1.7
Level NTC uses no ERTMS/ETCS track-train information except to announce/command level transitions and specific commands related to balise transmission. Eurobalises therefore still have to be read.
- kind: ordinary
- WordTraceId: 13564
- implementerEnhanced: Level NTC uses no ERTMS/ETCS track-train information except to announce/command level transitions and specific commands related to
  balise
  [EXTERNAL]
  transmission.
  Eurobalises
  [EXTERNAL]
  therefore still have to be read.
- implement: true
- atomic: false
- Legal Obligation: unknown

###### 2.6.4.1.8
The information displayed to the driver depends on the functionality of the underlying national system. The active national system is indicated to the driver as part of that information. Full train data has to be entered in order not to have to stop a train at a level transition position and to supervise maximum train speed.
- kind: ordinary
- WordTraceId: 13761
- implementerEnhanced: The information displayed to the
  driver
  [EXTERNAL]
  depends on the functionality of the underlying
  national system
  [EXTERNAL]
  . The active
  national system
  [EXTERNAL]
  is indicated to the
  driver
  [EXTERNAL]
  as part of that information. Full train data has to be entered in order not to have to stop a train at a level transition position and to supervise maximum train speed.
- implement: true
- atomic: false
- Legal Obligation: unknown

###### 2.6.4.1.9
A combination of national systems can be regarded as one NTC level.
- kind: ordinary
- WordTraceId: 14088
- implement: true
- atomic: true
- Legal Obligation: unknown

###### 2.6.4.1.10
Depending on the functionality and the configuration of the specific national system installed onboard, the ERTMS/ETCS Onboard system may need to be interfaced to it, in order to perform the transitions from/to the national system and/or in order to give access to ERTMS/ETCS Onboard resources (e.g. DMI). This can be achieved through a device called an STM (Specific Transmission Module) using a standardised interface.
- kind: ordinary
- WordTraceId: 14156
- implementerEnhanced: Depending on the functionality and the configuration of the specific
  national system
  [EXTERNAL]
  installed onboard, the
  ERTMS/ETCS Onboard
  [SELF]
  system may need to be interfaced to it, in order to perform the transitions from/to the
  national system
  [EXTERNAL]
  and/or in order to give access to
  ERTMS/ETCS Onboard
  [SELF]
  resources (
  e.g.
  [WEAK]
  DMI). This can be achieved through a device called an STM (Specific Transmission Module) using a standardised interface.
- implement: true
- atomic: false
- Legal Obligation: optional

###### 2.6.4.1.11
Intentionally deleted.
- kind: Placeholder
- WordTraceId: 14577
- implement: false
- atomic: false
- Legal Obligation: not applicable

###### 2.6.4.1.11[2]
- kind: Placeholder
- WordTraceId: 14601
- implement: false
- atomic: false
- Legal Obligation: not applicable

###### 2.6.4.1.11[2].[f]3
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- kind: Figure
- WordTraceId: 14620
- implement: false
- atomic: false
- Legal Obligation: not applicable

###### 2.6.4.1.11[2].[f]3.C
Figure {Figure 3}: ERTMS/ETCS Application Level NTC
- kind: Figure
- WordTraceId: 14620
- implementerEnhanced: Figure 3: ERTMS/ETCS Application Level NTC
- implement: false
- atomic: true
- Legal Obligation: unknown

##### 2.6.4.2
Summary of characteristics of Application Level NTC
- kind: Heading
- WordTraceId: 14688
- implement: false
- atomic: false
- Legal Obligation: not applicable

###### 2.6.4.2.1
Trackside equipment:
- kind: Heading
- WordTraceId: 14740
- implementerEnhanced: Trackside
  [EXTERNAL]
  equipment:
- implement: false
- atomic: true
- Legal Obligation: unknown

###### 2.6.4.2.1.*[1]
Level NTC uses the track-train transmission system from an underlying national system, which is not part of ERTMS/ETCS.
- kind: ordinary
- WordTraceId: 14762
- implementerEnhanced: Level NTC uses the track-train transmission system from an underlying
  national system
  [EXTERNAL]
  , which is not part of ERTMS/ETCS.
- implement: true
- atomic: true
- Legal Obligation: unknown
- ListNumberText: ·

###### 2.6.4.2.1.*[2]
For level transition purposes Eurobalises are used.
- kind: ordinary
- WordTraceId: 14882
- implementerEnhanced: For level transition purposes
  Eurobalises
  [EXTERNAL]
  are used.
- implement: true
- atomic: true
- Legal Obligation: unknown
- ListNumberText: ·

###### 2.6.4.2.2
Main ERTMS/ETCS trackside functions:
- kind: Heading
- WordTraceId: 14934
- implementerEnhanced: Main ERTMS/ETCS
  trackside
  [EXTERNAL]
  functions:
- implement: false
- atomic: true
- Legal Obligation: unknown

###### 2.6.4.2.2.*[1]
None.
- kind: ordinary
- WordTraceId: 14971
- implement: true
- atomic: true
- Legal Obligation: unknown
- ListNumberText: ·

###### 2.6.4.2.3
On-board equipment:
- kind: Heading
- WordTraceId: 14977
- implementerEnhanced: On-board equipment
  [SELF]
  :
- implement: false
- atomic: true
- Legal Obligation: unknown

###### 2.6.4.2.3.*[1]
Onboard equipment with Eurobalise transmission.
- kind: ordinary
- WordTraceId: 14998
- implementerEnhanced: Onboard equipment
  [SELF]
  with
  Eurobalise
  [EXTERNAL]
  transmission.
- implement: true
- atomic: true
- Legal Obligation: unknown
- ListNumberText: ·

###### 2.6.4.2.3.*[2]
Onboard part of the national system.
- kind: ordinary
- WordTraceId: 15046
- implementerEnhanced: Onboard part of the
  national system
  [EXTERNAL]
  .
- implement: true
- atomic: true
- Legal Obligation: unknown
- ListNumberText: ·

###### 2.6.4.2.4
Main ERTMS/ETCS on-board function:
- kind: Heading
- WordTraceId: 15083
- implementerEnhanced: Main
  ERTMS/ETCS on-board
  [SELF]
  function:
- implement: false
- atomic: true
- Legal Obligation: unknown

###### 2.6.4.2.4.*[1]
No train supervision, it is fully handed over to the national system.
- kind: ordinary
- WordTraceId: 15118
- implementerEnhanced: No train supervision, it is fully handed over to the
  national system
  [EXTERNAL]
  .
- implement: true
- atomic: true
- Legal Obligation: unknown
- ListNumberText: ·

###### 2.6.4.2.4.*[2]
Reading of Eurobalises to detect level transitions and certain special commands. All other messages are rejected.
- kind: ordinary
- WordTraceId: 15189
- implementerEnhanced: Reading of
  Eurobalises
  [EXTERNAL]
  to detect level transitions and certain special commands. All other messages are rejected.
- implement: true
- atomic: false
- Legal Obligation: unknown
- ListNumberText: ·

###### 2.6.4.2.4.*[3]
Management of the national system through STM, in case the ERTMS/ETCS on-board equipment is interfaced to the national system through an STM.
- kind: ordinary
- WordTraceId: 15303
- implementerEnhanced: Management of the
  national system
  [EXTERNAL]
  through STM,
  in case
  [CONDITION]
  the
  ERTMS/ETCS on-board equipment
  [SELF]
  is interfaced to the
  national system
  [EXTERNAL]
  through an STM.
- implement: true
- atomic: true
- Legal Obligation: unknown
- ListNumberText: ·

###### 2.6.4.2.4.*[4]
No cab signalling.
- kind: ordinary
- WordTraceId: 15445
- implement: true
- atomic: true
- Legal Obligation: unknown
- ListNumberText: ·

#### 2.6.5
ERTMS/ETCS Application Level 1
- kind: Heading
- WordTraceId: 15464
- implement: false
- atomic: false
- Legal Obligation: not applicable

##### 2.6.5.1
General description
- kind: Heading
- WordTraceId: 15495
- implement: false
- atomic: false
- Legal Obligation: not applicable

###### 2.6.5.1.1
ERTMS/ETCS Level 1 is a spot transmission based train control system to be used as an overlay on an underlying signalling system.
- kind: ordinary
- WordTraceId: 15515
- implement: true
- atomic: true
- Legal Obligation: unknown

###### 2.6.5.1.2
Movement authorities are generated trackside and are transmitted to the train via Eurobalises.
- kind: ordinary
- WordTraceId: 15645
- implementerEnhanced: Movement authorities are generated
  trackside
  [EXTERNAL]
  and are transmitted to the train via
  Eurobalises
  [EXTERNAL]
  .
- implement: true
- atomic: true
- Legal Obligation: unknown

###### 2.6.5.1.3
ERTMS/ETCS Level 1 provides a continuous speed supervision system, which also protects against overrun of the authority.
- kind: ordinary
- WordTraceId: 15742
- implement: true
- atomic: true
- Legal Obligation: unknown

###### 2.6.5.1.4
Train detection and train integrity supervision are performed by the trackside equipment of the underlying signalling system (interlocking, track circuits etc.) and are outside the scope of ERTMS/ETCS.
- kind: ordinary
- WordTraceId: 15864
- implementerEnhanced: Train detection and train integrity supervision are performed by the
  trackside
  [EXTERNAL]
  equipment of the underlying signalling system (interlocking, track circuits
  etc.
  [WEAK]
  ) and are outside the scope of ERTMS/ETCS.
- implement: true
- atomic: true
- Legal Obligation: unknown

###### 2.6.5.1.5
Level 1 is based on Eurobalises as spot transmission devices.
- kind: ordinary
- WordTraceId: 16066
- implementerEnhanced: Level 1 is based on
  Eurobalises
  [EXTERNAL]
  as spot transmission devices.
- implement: true
- atomic: true
- Legal Obligation: unknown

###### 2.6.5.1.6
The trackside equipment does not know the train to which it sends information.
- kind: ordinary
- WordTraceId: 16130
- implementerEnhanced: The
  trackside
  [EXTERNAL]
  equipment does not know the train to which it sends information.
- implement: true
- atomic: true
- Legal Obligation: unknown

###### 2.6.5.1.7
If in level 1 a lineside signal clears, an approaching train can not receive this information until it passes the Eurobalise group at that signal. The driver therefore has to observe the lineside signal to know when to proceed. The train has then to be permitted to approach the stopping location below a maximum permitted release speed.
- kind: ordinary
- WordTraceId: 16209
- implementerEnhanced: If
  [CONDITION]
  in level 1 a lineside signal clears, an approaching train can not receive this information
  until
  [TIME]
  it passes the
  Eurobalise
  [EXTERNAL]
  group at that signal. The
  driver
  [EXTERNAL]
  therefore has to observe the lineside signal to know
  when
  [CONDITION]
  to proceed. The train has then to be permitted to approach the stopping location
  below
  [WEAK]
  a maximum permitted release speed.
- implement: true
- atomic: false
- Legal Obligation: unknown

###### 2.6.5.1.8
Additional Eurobalises can be placed between distant and main signals to transmit infill information, the train will receive new information before reaching the signal.
- kind: ordinary
- WordTraceId: 16548
- implementerEnhanced: Additional
  Eurobalises
  [EXTERNAL]
  can be placed between distant and main signals to transmit infill information, the train will receive new information before reaching the signal.
- implement: true
- atomic: true
- Legal Obligation: unknown

###### 2.6.5.1.9
Note: Lineside signals are required in level 1 applications, except if semi-continuous infill is provided.
- kind: Note
- WordTraceId: 16718
- implementerEnhanced: Note: Lineside signals are required in level 1 applications, except
  if
  [CONDITION]
  semi-continuous infill is provided.
- implement: false
- atomic: false
- Legal Obligation: not applicable

###### 2.6.5.1.10
Semi-continuous infill can be provided using Euroloop or radio infill. In this case, the on-board system will be able to show new information to the driver as soon as it is available and even at standstill.
- kind: ordinary
- WordTraceId: 16825
- implementerEnhanced: Semi-continuous infill can be provided using
  Euroloop
  [EXTERNAL]
  or radio infill. In this case, the on-board system will be able to show new information to the
  driver
  [EXTERNAL]
  as soon as
  [WEAK]
  it is available and even at standstill.
- implement: true
- atomic: false
- Legal Obligation: unknown

###### 2.6.5.1.11
Euroloop or radio infill can improve the safety of a level 1 system as they allow the operation without release speed.
- kind: ordinary
- WordTraceId: 17033
- implementerEnhanced: Euroloop
  [EXTERNAL]
  or radio infill can improve the safety of a level 1 system as they allow the operation without release speed.
- implement: true
- atomic: true
- Legal Obligation: unknown

###### 2.6.5.1.11[2]
- kind: Placeholder
- WordTraceId: 17152
- implement: false
- atomic: false
- Legal Obligation: not applicable

###### 2.6.5.1.11[2].[f]4
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- kind: Figure
- WordTraceId: 17171
- implement: false
- atomic: false
- Legal Obligation: not applicable

###### 2.6.5.1.11[2].[f]4.C
Figure {Figure 4}: ERTMS/ETCS Application Level 1 without infill function
- kind: Figure
- WordTraceId: 17171
- implementerEnhanced: Figure 4: ERTMS/ETCS Application Level 1 without infill function
- implement: false
- atomic: true
- Legal Obligation: unknown

###### 2.6.5.1.11[3]
- kind: Placeholder
- WordTraceId: 17261
- implement: false
- atomic: false
- Legal Obligation: not applicable

###### 2.6.5.1.11[3].[f]5
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- kind: Figure
- WordTraceId: 17289
- implement: false
- atomic: false
- Legal Obligation: not applicable

###### 2.6.5.1.11[3].[f]5.C
Figure {Figure 5}: ERTMS/ETCS Application Level 1 with infill function by Euroloop or Radio infill
- kind: Figure
- WordTraceId: 17289
- implementerEnhanced: Figure 5: ERTMS/ETCS Application Level 1 with infill function by
  Euroloop
  [EXTERNAL]
  or Radio infill
- implement: false
- PlainText: Figure 5: ERTMS/ETCS Application Level 1 with infill function by Euroloop or Radio infill
- atomic: true
- Legal Obligation: unknown

##### 2.6.5.2
Summary of characteristics of Application Level 1
- kind: Heading
- WordTraceId: 17404
- implement: false
- atomic: false
- Legal Obligation: not applicable

###### 2.6.5.2.1
Trackside equipment:
- kind: Heading
- WordTraceId: 17454
- implementerEnhanced: Trackside
  [EXTERNAL]
  equipment:
- implement: false
- atomic: true
- Legal Obligation: unknown

###### 2.6.5.2.1.*[1]
Eurobalises for spot transmission from track to train.
- kind: ordinary
- WordTraceId: 17476
- implementerEnhanced: Eurobalises
  [EXTERNAL]
  for spot transmission from track to train.
- implement: true
- atomic: true
- Legal Obligation: unknown
- ListNumberText: ·

###### 2.6.5.2.1.*[2]
Eurobalises must be able to transmit variable information.
- kind: ordinary
- WordTraceId: 17532
- implementerEnhanced: Eurobalises
  [EXTERNAL]
  must be able to transmit variable information.
- implement: true
- atomic: true
- Legal Obligation: unknown
- ListNumberText: ·

###### 2.6.5.2.1.*[3]
Semi continuous infill transmission by using Euroloop or radio infill is optional.
- kind: ordinary
- WordTraceId: 17591
- implementerEnhanced: Semi continuous infill transmission by using
  Euroloop
  [EXTERNAL]
  or radio infill is optional.
- implement: true
- atomic: true
- Legal Obligation: unknown
- ListNumberText: ·

###### 2.6.5.2.2
Main ERTMS/ETCS trackside function:
- kind: Heading
- WordTraceId: 17674
- implementerEnhanced: Main ERTMS/ETCS
  trackside
  [EXTERNAL]
  function:
- implement: false
- atomic: true
- Legal Obligation: unknown

###### 2.6.5.2.2.*[1]
Determine movement authorities according to the underlying signalling system.
- kind: ordinary
- WordTraceId: 17710
- implement: true
- atomic: true
- Legal Obligation: unknown
- ListNumberText: ·

###### 2.6.5.2.2.*[2]
Transmit movement authorities and track description data to the train.
- kind: ordinary
- WordTraceId: 17788
- implement: true
- atomic: true
- Legal Obligation: unknown
- ListNumberText: ·

###### 2.6.5.2.3
On-board equipment:
- kind: Heading
- WordTraceId: 17861
- implementerEnhanced: On-board equipment
  [SELF]
  :
- implement: false
- atomic: true
- Legal Obligation: unknown

###### 2.6.5.2.3.*[1]
Onboard equipment with Eurobalise transmission.
- kind: ordinary
- WordTraceId: 17881
- implementerEnhanced: Onboard equipment
  [SELF]
  with
  Eurobalise
  [EXTERNAL]
  transmission.
- implement: true
- atomic: true
- Legal Obligation: unknown
- ListNumberText: ·

###### 2.6.5.2.3.*[2]
Euroloop transmission if infill by Euroloop is required.
- kind: ordinary
- WordTraceId: 17929
- implementerEnhanced: Euroloop
  [EXTERNAL]
  transmission
  if
  [CONDITION]
  infill by
  Euroloop
  [EXTERNAL]
  is required.
- implement: true
- atomic: true
- Legal Obligation: unknown
- ListNumberText: ·

###### 2.6.5.2.3.*[3]
Radio infill transmission if infill by radio is required.
- kind: ordinary
- WordTraceId: 17986
- implementerEnhanced: Radio infill transmission
  if
  [CONDITION]
  infill by radio is required.
- implement: true
- atomic: true
- Legal Obligation: unknown
- ListNumberText: ·

###### 2.6.5.2.4
Main ERTMS/ETCS on-board function:
- kind: Heading
- WordTraceId: 18044
- implementerEnhanced: Main
  ERTMS/ETCS on-board
  [SELF]
  function:
- implement: false
- atomic: true
- Legal Obligation: unknown

###### 2.6.5.2.4.*[1]
Reception of movement authority and track description related to the transmitting balise.
- kind: ordinary
- WordTraceId: 18079
- implementerEnhanced: Reception of movement authority and track description related to the transmitting
  balise
  [EXTERNAL]
  .
- implement: true
- atomic: true
- Legal Obligation: unknown
- ListNumberText: ·

###### 2.6.5.2.4.*[2]
Selection of the most restrictive value of the different speeds permitted at each location ahead.
- kind: ordinary
- WordTraceId: 18169
- implement: true
- atomic: true
- Legal Obligation: unknown
- ListNumberText: ·

###### 2.6.5.2.4.*[3]
Calculation of a dynamic speed profile taking into account the train running/braking characteristics which are known on-board and the track description data.
- kind: ordinary
- WordTraceId: 18267
- implement: true
- atomic: true
- Legal Obligation: unknown
- ListNumberText: ·

###### 2.6.5.2.4.*[4]
Comparison of the train speed with the permitted speed and commanding of the brake application if necessary.
- kind: ordinary
- WordTraceId: 18425
- implementerEnhanced: Comparison of the train speed with the permitted speed and commanding of the brake application
  if
  [CONDITION]
  necessary
  [WEAK]
  .
- implement: true
- atomic: true
- Legal Obligation: unknown
- ListNumberText: ·

###### 2.6.5.2.4.*[5]
Cab signalling to the driver.
- kind: ordinary
- WordTraceId: 18535
- implementerEnhanced: Cab signalling to the
  driver
  [EXTERNAL]
  .
- implement: true
- atomic: true
- Legal Obligation: unknown
- ListNumberText: ·

#### 2.6.6
ERTMS/ETCS Application Level 2
- kind: Heading
- WordTraceId: 18566
- implement: false
- atomic: false
- Legal Obligation: not applicable

##### 2.6.6.1
General description
- kind: Heading
- WordTraceId: 18597
- implement: false
- atomic: false
- Legal Obligation: not applicable

###### 2.6.6.1.1
ERTMS/ETCS Level 2 is a radio based train control system which is used as an overlay on an underlying signalling system.
- kind: ordinary
- WordTraceId: 18617
- implement: true
- atomic: true
- Legal Obligation: unknown

###### 2.6.6.1.2
Movement authorities are generated trackside and are transmitted to the train via Euroradio.
- kind: ordinary
- WordTraceId: 18739
- implementerEnhanced: Movement authorities are generated
  trackside
  [EXTERNAL]
  and are transmitted to the train via Euroradio.
- implement: true
- atomic: true
- Legal Obligation: unknown

###### 2.6.6.1.3
ERTMS/ETCS Level 2 provides a continuous speed supervision system, which also protects against overrun of the authority.
- kind: ordinary
- WordTraceId: 18833
- implement: true
- atomic: true
- Legal Obligation: unknown

###### 2.6.6.1.4
Train detection and train integrity supervision are performed by the trackside equipment of the underlying signalling system (interlocking, track circuits etc.) and are outside the scope of ERTMS/ETCS.
- kind: ordinary
- WordTraceId: 18955
- implementerEnhanced: Train detection and train integrity supervision are performed by the
  trackside
  [EXTERNAL]
  equipment of the underlying signalling system (interlocking, track circuits
  etc.
  [WEAK]
  ) and are outside the scope of ERTMS/ETCS.
- implement: true
- atomic: true
- Legal Obligation: unknown

###### 2.6.6.1.5
Level 2 is based on Euroradio for track to train communication and on Eurobalises as spot transmission devices mainly for location referencing.
- kind: ordinary
- WordTraceId: 19157
- implementerEnhanced: Level 2 is based on Euroradio for track to train communication and on
  Eurobalises
  [EXTERNAL]
  as spot transmission devices mainly for location referencing.
- implement: true
- atomic: true
- Legal Obligation: unknown

###### 2.6.6.1.6
The trackside radio block centre which provides the information to the trains knows each ERTMS/ETCS controlled train individually by the ERTMS/ETCS identity of its leading ERTMS/ETCS on-board equipment.
- kind: ordinary
- WordTraceId: 19303
- implementerEnhanced: The
  trackside
  [EXTERNAL]
  radio block centre
  [EXTERNAL]
  which provides the information to the trains knows each ERTMS/ETCS controlled train individually by the ERTMS/ETCS identity of its leading
  ERTMS/ETCS on-board equipment
  [SELF]
  .
- implement: true
- atomic: true
- Legal Obligation: unknown

###### 2.6.6.1.7
Note: Lineside signals can be suppressed in Level 2.
- kind: Note
- WordTraceId: 19507
- implement: false
- atomic: false
- Legal Obligation: not applicable

###### 2.6.6.1.7[2]
- kind: Placeholder
- WordTraceId: 19560
- implement: false
- atomic: false
- Legal Obligation: not applicable

###### 2.6.6.1.7[2].[f]6
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- kind: Figure
- WordTraceId: 19577
- implement: false
- atomic: false
- Legal Obligation: not applicable

###### 2.6.6.1.7[2].[f]6.C
Figure {Figure 6}: ERTMS/ETCS Application Level 2
- kind: Figure
- WordTraceId: 19577
- implementerEnhanced: Figure 6: ERTMS/ETCS Application Level 2
- implement: false
- PlainText: Figure 6: ERTMS/ETCS Application Level 2
- atomic: true
- Legal Obligation: unknown

##### 2.6.6.2
Summary of characteristics of Application Level 2
- kind: Heading
- WordTraceId: 19645
- implement: false
- atomic: false
- Legal Obligation: not applicable

###### 2.6.6.2.1
Trackside equipment:
- kind: Heading
- WordTraceId: 19695
- implementerEnhanced: Trackside
  [EXTERNAL]
  equipment:
- implement: false
- atomic: true
- Legal Obligation: unknown

###### 2.6.6.2.1.*[1]
Radio block centre.
- kind: ordinary
- WordTraceId: 19717
- implementerEnhanced: Radio block centre
  [EXTERNAL]
  .
- implement: true
- atomic: true
- Legal Obligation: unknown
- ListNumberText: ·

###### 2.6.6.2.1.*[2]
Euroradio for bi-directional track-train communication.
- kind: ordinary
- WordTraceId: 19737
- implement: true
- atomic: true
- Legal Obligation: unknown
- ListNumberText: ·

###### 2.6.6.2.1.*[3]
Eurobalises mainly for location referencing.
- kind: ordinary
- WordTraceId: 19793
- implementerEnhanced: Eurobalises
  [EXTERNAL]
  mainly for location referencing.
- implement: true
- atomic: true
- Legal Obligation: unknown
- ListNumberText: ·

###### 2.6.6.2.2
Main ERTMS/ETCS trackside function:
- kind: Heading
- WordTraceId: 19839
- implementerEnhanced: Main ERTMS/ETCS
  trackside
  [EXTERNAL]
  function:
- implement: false
- atomic: true
- Legal Obligation: unknown

###### 2.6.6.2.2.*[1]
Knowing each train equipped with and running under ERTMS/ETCS within an RBC area by its ERTMS/ETCS identity.
- kind: ordinary
- WordTraceId: 19875
- implementerEnhanced: Knowing each train equipped with and running under ERTMS/ETCS within an
  RBC
  [EXTERNAL]
  area by its ERTMS/ETCS identity.
- implement: true
- atomic: true
- Legal Obligation: unknown
- ListNumberText: ·

###### 2.6.6.2.2.*[2]
Following each ERTMS/ETCS controlled train’s location within an RBC area.
- kind: ordinary
- WordTraceId: 19985
- implementerEnhanced: Following each ERTMS/ETCS controlled train’s location within an
  RBC
  [EXTERNAL]
  area.
- implement: true
- atomic: true
- Legal Obligation: unknown
- ListNumberText: ·

###### 2.6.6.2.2.*[3]
Determine movement authorities according to the underlying signalling system for each train individually.
- kind: ordinary
- WordTraceId: 20060
- implementerEnhanced: Determine movement authorities according to the underlying signalling system
  for each
  [LOOP]
  train individually.
- implement: true
- atomic: true
- Legal Obligation: unknown
- ListNumberText: ·

###### 2.6.6.2.2.*[4]
Transmit movement authorities and track description to each train individually.
- kind: ordinary
- WordTraceId: 20166
- implement: true
- atomic: true
- Legal Obligation: unknown
- ListNumberText: ·

###### 2.6.6.2.2.*[5]
Handing over of train control between different RBC’s at the RBC-RBC borders.
- kind: ordinary
- WordTraceId: 20248
- implement: true
- atomic: true
- Legal Obligation: unknown
- ListNumberText: ·

###### 2.6.6.2.3
On-board equipment:
- kind: Heading
- WordTraceId: 20326
- implementerEnhanced: On-board equipment
  [SELF]
  :
- implement: false
- atomic: true
- Legal Obligation: unknown

###### 2.6.6.2.3.*[1]
Onboard equipment with Eurobalise and Euroradio transmissions.
- kind: ordinary
- WordTraceId: 20347
- implementerEnhanced: Onboard equipment
  [SELF]
  with
  Eurobalise
  [EXTERNAL]
  and Euroradio transmissions.
- implement: true
- atomic: true
- Legal Obligation: unknown
- ListNumberText: ·

###### 2.6.6.2.4
Main ERTMS/ETCS on-board function:
- kind: Heading
- WordTraceId: 20410
- implementerEnhanced: Main
  ERTMS/ETCS on-board
  [SELF]
  function:
- implement: false
- atomic: true
- Legal Obligation: unknown

###### 2.6.6.2.4.*[1]
The train reads Eurobalises and sends its position relative to the detected balises to the radio block centre.
- kind: ordinary
- WordTraceId: 20445
- implementerEnhanced: The train reads
  Eurobalises
  [EXTERNAL]
  and sends its position relative to the detected
  balises
  [EXTERNAL]
  to the
  radio block centre
  [EXTERNAL]
  .
- implement: true
- atomic: true
- Legal Obligation: unknown
- ListNumberText: ·

###### 2.6.6.2.4.*[2]
The train receives a movement authority and the track description via Euroradio relating to a balise.
- kind: ordinary
- WordTraceId: 20556
- implementerEnhanced: The train receives a movement authority and the track description via Euroradio relating to a
  balise
  [EXTERNAL]
  .
- implement: true
- atomic: true
- Legal Obligation: unknown
- ListNumberText: ·

###### 2.6.6.2.4.*[3]
Selection of the most restrictive value of the different speeds permitted at each location ahead.
- kind: ordinary
- WordTraceId: 20660
- implement: true
- atomic: true
- Legal Obligation: unknown
- ListNumberText: ·

###### 2.6.6.2.4.*[4]
Calculation of a dynamic speed profile taking into account the train running/braking characteristics which are known on-board and the track description data.
- kind: ordinary
- WordTraceId: 20758
- implement: true
- atomic: true
- Legal Obligation: unknown
- ListNumberText: ·

###### 2.6.6.2.4.*[5]
Comparison of the train speed with the permitted speed and commanding of the brake application if necessary.
- kind: ordinary
- WordTraceId: 20916
- implementerEnhanced: Comparison of the train speed with the permitted speed and commanding of the brake application
  if
  [CONDITION]
  necessary
  [WEAK]
  .
- implement: true
- atomic: true
- Legal Obligation: unknown
- ListNumberText: ·

###### 2.6.6.2.4.*[6]
Cab signalling to the driver.
- kind: ordinary
- WordTraceId: 21026
- implementerEnhanced: Cab signalling to the
  driver
  [EXTERNAL]
  .
- implement: true
- atomic: true
- Legal Obligation: unknown
- ListNumberText: ·

#### 2.6.7
ERTMS/ETCS Application Level 3
- kind: Heading
- WordTraceId: 21057
- implement: false
- atomic: false
- Legal Obligation: not applicable

##### 2.6.7.1
General description
- kind: Heading
- WordTraceId: 21088
- implement: false
- atomic: false
- Legal Obligation: not applicable

###### 2.6.7.1.1
ERTMS/ETCS Level 3 is a radio based train control system.
- kind: ordinary
- WordTraceId: 21108
- implement: true
- atomic: true
- Legal Obligation: unknown

###### 2.6.7.1.2
Movement authorities are generated trackside and are transmitted to the train via Euroradio.
- kind: ordinary
- WordTraceId: 21166
- implementerEnhanced: Movement authorities are generated
  trackside
  [EXTERNAL]
  and are transmitted to the train via Euroradio.
- implement: true
- atomic: true
- Legal Obligation: unknown

###### 2.6.7.1.3
ERTMS/ETCS Level 3 provides a continuous speed supervision system, which also protects against overrun of the authority.
- kind: ordinary
- WordTraceId: 21260
- implement: true
- atomic: true
- Legal Obligation: unknown

###### 2.6.7.1.4
Train position and train integrity supervision are performed by the trackside radio block centre in co-operation with the train (which sends position reports and train integrity information).
- kind: ordinary
- WordTraceId: 21382
- implementerEnhanced: Train position and train integrity supervision are performed by the
  trackside
  [EXTERNAL]
  radio block centre
  [EXTERNAL]
  in co-operation with the train (which sends position reports and train integrity information).
- implement: true
- atomic: true
- Legal Obligation: unknown

###### 2.6.7.1.5
Level 3 is based on Euroradio for track to train communication and on Eurobalises as spot transmission devices mainly for location referencing.
- kind: ordinary
- WordTraceId: 21575
- implementerEnhanced: Level 3 is based on Euroradio for track to train communication and on
  Eurobalises
  [EXTERNAL]
  as spot transmission devices mainly for location referencing.
- implement: true
- atomic: true
- Legal Obligation: unknown

###### 2.6.7.1.6
The trackside radio block centre which provides the information to the trains knows each train individually by the ERTMS/ETCS identity of its leading ERTMS/ETCS on-board equipment.
- kind: ordinary
- WordTraceId: 21721
- implementerEnhanced: The
  trackside
  [EXTERNAL]
  radio block centre
  [EXTERNAL]
  which provides the information to the trains knows each train individually by the ERTMS/ETCS identity of its leading
  ERTMS/ETCS on-board equipment
  [SELF]
  .
- implement: true
- atomic: true
- Legal Obligation: unknown

###### 2.6.7.1.7
Note: Lineside signals are not foreseen to be used when operating in Level 3.
- kind: Note
- WordTraceId: 21903
- implementerEnhanced: Note: Lineside signals are not foreseen to be used
  when
  [CONDITION]
  operating in Level 3.
- implement: false
- atomic: false
- Legal Obligation: not applicable

###### 2.6.7.1.7[2]
- kind: Placeholder
- WordTraceId: 21981
- implement: false
- atomic: false
- Legal Obligation: not applicable

###### 2.6.7.1.7[2].[f]7
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- kind: Figure
- WordTraceId: 21999
- implement: false
- atomic: false
- Legal Obligation: not applicable

###### 2.6.7.1.7[2].[f]7.C
Figure {Figure 7}: ERTMS/ETCS Application Level 3
- kind: Figure
- WordTraceId: 21999
- implementerEnhanced: Figure 7: ERTMS/ETCS Application Level 3
- implement: false
- PlainText: Figure 7: ERTMS/ETCS Application Level 3
- atomic: true
- Legal Obligation: unknown

##### 2.6.7.2
Summary of characteristics of Application Level 3
- kind: Heading
- WordTraceId: 22065
- implement: false
- atomic: false
- Legal Obligation: not applicable

###### 2.6.7.2.1
Trackside equipment:
- kind: Heading
- WordTraceId: 22115
- implementerEnhanced: Trackside
  [EXTERNAL]
  equipment:
- implement: false
- atomic: true
- Legal Obligation: unknown

###### 2.6.7.2.1.*[1]
Radio block centre.
- kind: ordinary
- WordTraceId: 22137
- implementerEnhanced: Radio block centre
  [EXTERNAL]
  .
- implement: true
- atomic: true
- Legal Obligation: unknown
- ListNumberText: ·

###### 2.6.7.2.1.*[2]
Euroradio for bi-directional track-train communication.
- kind: ordinary
- WordTraceId: 22157
- implement: true
- atomic: true
- Legal Obligation: unknown
- ListNumberText: ·

###### 2.6.7.2.1.*[3]
Eurobalises for mainly location referencing.
- kind: ordinary
- WordTraceId: 22213
- implementerEnhanced: Eurobalises
  [EXTERNAL]
  for mainly location referencing.
- implement: true
- atomic: true
- Legal Obligation: unknown
- ListNumberText: ·

###### 2.6.7.2.2
Main ERTMS/ETCS trackside function:
- kind: Heading
- WordTraceId: 22259
- implementerEnhanced: Main ERTMS/ETCS
  trackside
  [EXTERNAL]
  function:
- implement: false
- atomic: true
- Legal Obligation: unknown

###### 2.6.7.2.2.*[1]
Knowing each train within an RBC area by its ERTMS/ETCS identity.
- kind: ordinary
- WordTraceId: 22295
- implementerEnhanced: Knowing each train within an
  RBC
  [EXTERNAL]
  area by its ERTMS/ETCS identity.
- implement: true
- atomic: true
- Legal Obligation: unknown
- ListNumberText: ·

###### 2.6.7.2.2.*[2]
Following each trains location within an RBC area.
- kind: ordinary
- WordTraceId: 22362
- implementerEnhanced: Following each trains location within an
  RBC
  [EXTERNAL]
  area.
- implement: true
- atomic: true
- Legal Obligation: unknown
- ListNumberText: ·

###### 2.6.7.2.2.*[3]
Route locking and route releasing based on information received from the trains.
- kind: ordinary
- WordTraceId: 22414
- implement: true
- atomic: true
- Legal Obligation: unknown
- ListNumberText: ·

###### 2.6.7.2.2.*[4]
Determine movement authorities for each train individually.
- kind: ordinary
- WordTraceId: 22495
- implementerEnhanced: Determine movement authorities
  for each
  [LOOP]
  train individually.
- implement: true
- atomic: true
- Legal Obligation: unknown
- ListNumberText: ·

###### 2.6.7.2.2.*[5]
Transmit movement authorities and track description to each train individually.
- kind: ordinary
- WordTraceId: 22556
- implement: true
- atomic: true
- Legal Obligation: unknown
- ListNumberText: ·

###### 2.6.7.2.2.*[6]
Handing over of train control between different RBC’s at the RBC-RBC borders.
- kind: ordinary
- WordTraceId: 22638
- implement: true
- atomic: true
- Legal Obligation: unknown
- ListNumberText: ·

###### 2.6.7.2.3
On-board equipment:
- kind: Heading
- WordTraceId: 22716
- implementerEnhanced: On-board equipment
  [SELF]
  :
- implement: false
- atomic: true
- Legal Obligation: unknown

###### 2.6.7.2.3.*[1]
Onboard equipment with Eurobalise and Euroradio transmissions.
- kind: ordinary
- WordTraceId: 22737
- implementerEnhanced: Onboard equipment
  [SELF]
  with
  Eurobalise
  [EXTERNAL]
  and Euroradio transmissions.
- implement: true
- atomic: true
- Legal Obligation: unknown
- ListNumberText: ·

###### 2.6.7.2.3.*[2]
Train integrity proving system.
- kind: ordinary
- WordTraceId: 22800
- implement: true
- atomic: true
- Legal Obligation: unknown
- ListNumberText: ·

###### 2.6.7.2.4
Main ERTMS/ETCS on-board functions:
- kind: Heading
- WordTraceId: 22832
- implementerEnhanced: Main
  ERTMS/ETCS on-board
  [SELF]
  functions:
- implement: false
- atomic: true
- Legal Obligation: unknown

###### 2.6.7.2.4.*[1]
The train reads Eurobalises and sends its position relative to the detected balises to the radio block centre.
- kind: ordinary
- WordTraceId: 22868
- implementerEnhanced: The train reads
  Eurobalises
  [EXTERNAL]
  and sends its position relative to the detected
  balises
  [EXTERNAL]
  to the
  radio block centre
  [EXTERNAL]
  .
- implement: true
- atomic: true
- Legal Obligation: unknown
- ListNumberText: ·

###### 2.6.7.2.4.*[2]
The train monitors train integrity (external function, not part of ERTMS/ETCS) and sends this information to the radio block centre.
- kind: ordinary
- WordTraceId: 22979
- implementerEnhanced: The train monitors train integrity (
  external
  [EXTERNAL]
  function, not part of ERTMS/ETCS) and sends this information to the
  radio block centre
  [EXTERNAL]
  .
- implement: true
- atomic: true
- Legal Obligation: unknown
- ListNumberText: ·

###### 2.6.7.2.4.*[3]
The train receives a movement authority and the track description via Euroradio relating to a balise.
- kind: ordinary
- WordTraceId: 23112
- implementerEnhanced: The train receives a movement authority and the track description via Euroradio relating to a
  balise
  [EXTERNAL]
  .
- implement: true
- atomic: true
- Legal Obligation: unknown
- ListNumberText: ·

###### 2.6.7.2.4.*[4]
Selection of the most restrictive value of the different speeds permitted at each location ahead.
- kind: ordinary
- WordTraceId: 23216
- implement: true
- atomic: true
- Legal Obligation: unknown
- ListNumberText: ·

###### 2.6.7.2.4.*[5]
Calculation of a dynamic speed profile, taking into account the train running/braking characteristics which are known on-board and the track description data.
- kind: ordinary
- WordTraceId: 23314
- implement: true
- atomic: true
- Legal Obligation: unknown
- ListNumberText: ·

###### 2.6.7.2.4.*[6]
Comparison of the train speed with the permitted speed and commanding of the brake application if necessary.
- kind: ordinary
- WordTraceId: 23473
- implementerEnhanced: Comparison of the train speed with the permitted speed and commanding of the brake application
  if
  [CONDITION]
  necessary
  [WEAK]
  .
- implement: true
- atomic: true
- Legal Obligation: unknown
- ListNumberText: ·

###### 2.6.7.2.4.*[7]
Cab signalling to the driver.
- kind: ordinary
- WordTraceId: 23583
- implementerEnhanced: Cab signalling to the
  driver
  [EXTERNAL]
  .
- implement: true
- atomic: true
- Legal Obligation: unknown
- ListNumberText: ·

#### 2.6.8
Level transitions
- kind: Heading
- WordTraceId: 23614
- implement: false
- atomic: false
- Legal Obligation: not applicable

##### 2.6.8.1
An ERTMS/ETCS equipment which is not isolated always operates in one of the above described levels. All transitions between these levels are performed according to defined functions and procedures.
- kind: ordinary
- WordTraceId: 23632
- implementerEnhanced: An ERTMS/ETCS equipment which is not isolated always operates in one of the
  above
  [WEAK]
  described levels. All transitions between these levels are performed according to defined functions and procedures.
- implement: true
- atomic: false
- Legal Obligation: unknown

##### 2.6.8.2
Additional national functions and rules which might be used by an individual railway to for example prevent not equipped trains from entering a level 2/3 area are not specified here and have to be implemented outside ERTMS/ETCS.
- kind: ordinary
- WordTraceId: 23831
- implementerEnhanced: Additional national functions and rules which might be used by an individual railway to
  for example
  [WEAK]
  prevent not equipped trains from entering a level 2/3 area are not specified here and have to be implemented outside ERTMS/ETCS.
- implement: true
- atomic: true
- Legal Obligation: unknown

##### 2.6.8.3
The following table shows all possible transitions (marked with Grey):
- kind: ordinary
- WordTraceId: 24060
- implement: true
- atomic: true
- Legal Obligation: unknown

##### 2.6.8.3[2]
- kind: Placeholder
- WordTraceId: 24131
- implement: false
- atomic: false
- Legal Obligation: not applicable

###### 2.6.8.3[2].[t]1
| [r][1].[c][1] to from | [r][1].[c][2] 0 | [r][1].[c][3] NTC | [r][1].[c][4] 1 | [r][1].[c][5] 2 | [r][1].[c][6] 3 |
| --- | --- | --- | --- | --- | --- |
| [r][2].[c][1] 0 | [r][2].[c][2] | [r][2].[c][3] | [r][2].[c][4] | [r][2].[c][5] | [r][2].[c][6] |
| [r][3].[c][1] NTC | [r][3].[c][2] | [r][3].[c][3] a) | [r][3].[c][4] | [r][3].[c][5] | [r][3].[c][6] |
| [r][4].[c][1] 1 | [r][4].[c][2] | [r][4].[c][3] | [r][4].[c][4] | [r][4].[c][5] | [r][4].[c][6] |
| [r][5].[c][1] 2 | [r][5].[c][2] | [r][5].[c][3] | [r][5].[c][4] | [r][5].[c][5] b) | [r][5].[c][6] |
| [r][6].[c][1] 3 | [r][6].[c][2] | [r][6].[c][3] | [r][6].[c][4] | [r][6].[c][5] | [r][6].[c][6] b) |
- kind: Table
- WordTraceId: 24217
- implement: false
- atomic: false
- Legal Obligation: not applicable

###### 2.6.8.3[2].[t]1.C
Table {Table 1}: Possible level transitions.
- kind: Table
- WordTraceId: 24217
- implementerEnhanced: Table 1: Possible level transitions.
- implement: false
- PlainText: Table 1: Possible level transitions.
- atomic: true
- Legal Obligation: unknown

###### 2.6.8.3[2].[t]1.[r][1]
- kind: Table
- WordTraceId: 24131
- implement: false
- atomic: false
- Legal Obligation: not applicable

###### 2.6.8.3[2].[t]1.[r][1].[c][1]
CONTENTS HAVE BEEN SPLIT UP - SEE CHILDREN
- kind: ordinary
- WordTraceId: 24131
- implement: false
- atomic: false
- Legal Obligation: not applicable

###### 2.6.8.3[2].[t]1.[r][1].[c][1].[1]
to
- kind: ordinary
- WordTraceId: 24131
- implement: true
- atomic: true
- Legal Obligation: unknown

###### 2.6.8.3[2].[t]1.[r][1].[c][1].[2]
from
- kind: ordinary
- WordTraceId: 24134
- implement: true
- atomic: true
- Legal Obligation: unknown

###### 2.6.8.3[2].[t]1.[r][1].[c][2]
0
- kind: ordinary
- WordTraceId: 24156
- implement: true
- atomic: true
- Legal Obligation: unknown

###### 2.6.8.3[2].[t]1.[r][1].[c][3]
NTC
- kind: ordinary
- WordTraceId: 24158
- implement: true
- atomic: true
- Legal Obligation: unknown

###### 2.6.8.3[2].[t]1.[r][1].[c][4]
1
- kind: ordinary
- WordTraceId: 24162
- implement: true
- atomic: true
- Legal Obligation: unknown

###### 2.6.8.3[2].[t]1.[r][1].[c][5]
2
- kind: ordinary
- WordTraceId: 24164
- implement: true
- atomic: true
- Legal Obligation: unknown

###### 2.6.8.3[2].[t]1.[r][1].[c][6]
3
- kind: ordinary
- WordTraceId: 24166
- implement: true
- atomic: true
- Legal Obligation: unknown

###### 2.6.8.3[2].[t]1.[r][2]
- kind: Table
- WordTraceId: 24169
- implement: false
- atomic: false
- Legal Obligation: not applicable

###### 2.6.8.3[2].[t]1.[r][2].[c][1]
0
- kind: ordinary
- WordTraceId: 24169
- implement: true
- atomic: true
- Legal Obligation: unknown

###### 2.6.8.3[2].[t]1.[r][2].[c][2]
- kind: ordinary
- WordTraceId: 24171
- implement: true
- atomic: true
- Legal Obligation: unknown

###### 2.6.8.3[2].[t]1.[r][2].[c][3]
- kind: ordinary
- WordTraceId: 24172
- implement: true
- atomic: true
- Legal Obligation: unknown

###### 2.6.8.3[2].[t]1.[r][2].[c][4]
- kind: ordinary
- WordTraceId: 24173
- implement: true
- atomic: true
- Legal Obligation: unknown

###### 2.6.8.3[2].[t]1.[r][2].[c][5]
- kind: ordinary
- WordTraceId: 24174
- implement: true
- atomic: true
- Legal Obligation: unknown

###### 2.6.8.3[2].[t]1.[r][2].[c][6]
- kind: ordinary
- WordTraceId: 24175
- implement: true
- atomic: true
- Legal Obligation: unknown

###### 2.6.8.3[2].[t]1.[r][3]
- kind: Table
- WordTraceId: 24177
- implement: false
- atomic: false
- Legal Obligation: not applicable

###### 2.6.8.3[2].[t]1.[r][3].[c][1]
NTC
- kind: ordinary
- WordTraceId: 24177
- implement: true
- atomic: true
- Legal Obligation: unknown

###### 2.6.8.3[2].[t]1.[r][3].[c][2]
- kind: ordinary
- WordTraceId: 24181
- implement: true
- atomic: true
- Legal Obligation: unknown

###### 2.6.8.3[2].[t]1.[r][3].[c][3]
a)
- kind: ordinary
- WordTraceId: 24182
- implement: true
- atomic: true
- Legal Obligation: unknown

###### 2.6.8.3[2].[t]1.[r][3].[c][4]
- kind: ordinary
- WordTraceId: 24185
- implement: true
- atomic: true
- Legal Obligation: unknown

###### 2.6.8.3[2].[t]1.[r][3].[c][5]
- kind: ordinary
- WordTraceId: 24186
- implement: true
- atomic: true
- Legal Obligation: unknown

###### 2.6.8.3[2].[t]1.[r][3].[c][6]
- kind: ordinary
- WordTraceId: 24187
- implement: true
- atomic: true
- Legal Obligation: unknown

###### 2.6.8.3[2].[t]1.[r][4]
- kind: Table
- WordTraceId: 24189
- implement: false
- atomic: false
- Legal Obligation: not applicable

###### 2.6.8.3[2].[t]1.[r][4].[c][1]
1
- kind: ordinary
- WordTraceId: 24189
- implement: true
- atomic: true
- Legal Obligation: unknown

###### 2.6.8.3[2].[t]1.[r][4].[c][2]
- kind: ordinary
- WordTraceId: 24191
- implement: true
- atomic: true
- Legal Obligation: unknown

###### 2.6.8.3[2].[t]1.[r][4].[c][3]
- kind: ordinary
- WordTraceId: 24192
- implement: true
- atomic: true
- Legal Obligation: unknown

###### 2.6.8.3[2].[t]1.[r][4].[c][4]
- kind: ordinary
- WordTraceId: 24193
- implement: true
- atomic: true
- Legal Obligation: unknown

###### 2.6.8.3[2].[t]1.[r][4].[c][5]
- kind: ordinary
- WordTraceId: 24194
- implement: true
- atomic: true
- Legal Obligation: unknown

###### 2.6.8.3[2].[t]1.[r][4].[c][6]
- kind: ordinary
- WordTraceId: 24195
- implement: true
- atomic: true
- Legal Obligation: unknown

###### 2.6.8.3[2].[t]1.[r][5]
- kind: Table
- WordTraceId: 24197
- implement: false
- atomic: false
- Legal Obligation: not applicable

###### 2.6.8.3[2].[t]1.[r][5].[c][1]
2
- kind: ordinary
- WordTraceId: 24197
- implement: true
- atomic: true
- Legal Obligation: unknown

###### 2.6.8.3[2].[t]1.[r][5].[c][2]
- kind: ordinary
- WordTraceId: 24199
- implement: true
- atomic: true
- Legal Obligation: unknown

###### 2.6.8.3[2].[t]1.[r][5].[c][3]
- kind: ordinary
- WordTraceId: 24200
- implement: true
- atomic: true
- Legal Obligation: unknown

###### 2.6.8.3[2].[t]1.[r][5].[c][4]
- kind: ordinary
- WordTraceId: 24201
- implement: true
- atomic: true
- Legal Obligation: unknown

###### 2.6.8.3[2].[t]1.[r][5].[c][5]
b)
- kind: ordinary
- WordTraceId: 24202
- implement: true
- atomic: true
- Legal Obligation: unknown

###### 2.6.8.3[2].[t]1.[r][5].[c][6]
- kind: ordinary
- WordTraceId: 24205
- implement: true
- atomic: true
- Legal Obligation: unknown

###### 2.6.8.3[2].[t]1.[r][6]
- kind: Table
- WordTraceId: 24207
- implement: false
- atomic: false
- Legal Obligation: not applicable

###### 2.6.8.3[2].[t]1.[r][6].[c][1]
3
- kind: ordinary
- WordTraceId: 24207
- implement: true
- atomic: true
- Legal Obligation: unknown

###### 2.6.8.3[2].[t]1.[r][6].[c][2]
- kind: ordinary
- WordTraceId: 24209
- implement: true
- atomic: true
- Legal Obligation: unknown

###### 2.6.8.3[2].[t]1.[r][6].[c][3]
- kind: ordinary
- WordTraceId: 24210
- implement: true
- atomic: true
- Legal Obligation: unknown

###### 2.6.8.3[2].[t]1.[r][6].[c][4]
- kind: ordinary
- WordTraceId: 24211
- implement: true
- atomic: true
- Legal Obligation: unknown

###### 2.6.8.3[2].[t]1.[r][6].[c][5]
- kind: ordinary
- WordTraceId: 24212
- implement: true
- atomic: true
- Legal Obligation: unknown

###### 2.6.8.3[2].[t]1.[r][6].[c][6]
b)
- kind: ordinary
- WordTraceId: 24213
- implement: true
- atomic: true
- Legal Obligation: unknown

###### 2.6.8.3[2].a
Transitions between level NTC and level NTC describe the switching from one national system to another national system.
- kind: ordinary
- WordTraceId: 24278
- implementerEnhanced: Transitions between level NTC and level NTC describe the switching from one
  national system
  [EXTERNAL]
  to another
  national system
  [EXTERNAL]
  .
- implement: true
- atomic: true
- Legal Obligation: unknown
- ListNumberText: a)

###### 2.6.8.3[2].b
Transitions between level 2 and level 2 respectively between level 3 and level 3 describe the handover between RBC’s.
- kind: ordinary
- WordTraceId: 24399
- implement: true
- atomic: true
- Legal Obligation: unknown
- ListNumberText: b)
