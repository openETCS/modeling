# IBM Rational DOORS, 23 January 2014

# Specification: SUBSET-026_SRS _Ch-8_v330
- ReqIF.Description: SUBSET-026_SRS _Ch-8_v330
- ReqIF.Name: SUBSET-026_SRS _Ch-8_v330

## 1 (New OpenETCS Requirement Type)

### 2: 8.1 Modification History (New OpenETCS Requirement Type)

### 3: 8.2 Table of Contents (New OpenETCS Requirement Type)

### 4: 8.3 Introduction (New OpenETCS Requirement Type)

#### 5: 8.3.1 Scope and Purpose (New OpenETCS Requirement Type)

##### 6: 8.3.1.1 This chapter defines the format and content of messages necessary for ERTMS/ETCS functions. (New OpenETCS Requirement Type)

##### 7: 8.3.1.2 Concerning the transmission media, this chapter does not cover considerations such as medium-specific use constraints (e.g. distance between track-circuit and balise…), as well as functions (e.g. detection of balise reference, time and location stamp, identifying type of receiving balise, Key Management, Releasing/maintaining a radio connection…) and performance of the transmission media. (New OpenETCS Requirement Type)

#### 8: 8.3.2 Definitions (New OpenETCS Requirement Type)

##### 9: 8.3.2.1 Transmission media considered hereafter are standard ERTMS/ETCS transmission media used for ETCS (Eurobalise, Euroradio and Euroloop). (New OpenETCS Requirement Type)

##### 10: 8.3.2.2 A message includes user data (application level) and protocol data (depending on the transmission medium). (New OpenETCS Requirement Type)

##### 11: 8.3.2.3 A Eurobalise message is the information sent by a balise group (i.e. the message is composed of one or several telegrams, sorted by balise number in the group (telegram from balise number 1 first), each telegram is transmitted by a Eurobalise). A Eurobalise telegram contains one header and an identified and coherent set of Packets. (New OpenETCS Requirement Type)

###### 12 (New OpenETCS Requirement Type)
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
###### 13 (New OpenETCS Requirement Type)
Figure 1: Composition of a balise group message

##### 14: 8.3.2.4 A Euroradio message contains one header and an identified and coherent set of variables (if needed) and Packets. (New OpenETCS Requirement Type)

##### 15: 8.3.2.5 A Euroloop message contains one header and an identified and coherent set of Packets. (New OpenETCS Requirement Type)

### 16: 8.4 Rules (New OpenETCS Requirement Type)

#### 17: 8.4.1 Common Rules (New OpenETCS Requirement Type)

##### 18: 8.4.1.1 A message (Euroradio/Euroloop) or telegram (Eurobalise) shall be composed of (New OpenETCS Requirement Type)

##### 19: One Header, (New OpenETCS Requirement Type)

##### 20: When needed, a predefined set of variables (only for Radio), (New OpenETCS Requirement Type)

##### 21: When needed, a predefined set of Packets (only for Radio), (New OpenETCS Requirement Type)

##### 22: Optional Packets as needed by application. (New OpenETCS Requirement Type)

##### 23: 8.4.1.2 The transmission order shall respect the order of data elements listed in the message format (from top to bottom). (New OpenETCS Requirement Type)

##### 24: 8.4.1.3 The behaviour of the receiver shall not depend on the sequence of the Packets given by the message. (New OpenETCS Requirement Type)

###### 25: 8.4.1.3.1 Exception for Infill information: The locations given in the packets following packet 136 (Infill Location Reference) shall be referred to the balise group indicated in such packet. (New OpenETCS Requirement Type)

###### 26: 8.4.1.3.2 Note: orientations are in any case always referred to the directionality of balise group (balise transmission), directionality of loop (Euroloop transmission) or directionality of LRBG (radio transmission). (New OpenETCS Requirement Type)

##### 27: 8.4.1.4 It shall be forbidden to send more instances of the same packet type for the same direction in the same message. (New OpenETCS Requirement Type)

###### 28: 8.4.1.4.1 Exception 1: A message can contain several packets 44 (Data used by applications outside the ERTMS/ETCS system). (New OpenETCS Requirement Type)

###### 29: 8.4.1.4.2 Exception 2: A message can contain several packets 65 (Temporary Speed Restriction). In case of revocable TSRs, the identities of the corresponding temporary speed restrictions (variable NID_TSR) transmitted in the same message shall be different. (New OpenETCS Requirement Type)

###### 30: 8.4.1.4.3 Exception 3: A message can contain several packets 66 (TSR Revocation). The identities of the corresponding temporary speed restrictions (variable NID_TSR) transmitted in the same message shall be different. (New OpenETCS Requirement Type)

###### 31: 8.4.1.4.4 Exception 4: A message transmitted by a balise group can contain one packet 136 per balise telegram per direction. Each packet 136 indicates which part of that telegram is to be considered as part of the infill information. Multiple packets 136 in balises of a balise group shall have identical content per direction. (New OpenETCS Requirement Type)

###### 32: 8.4.1.4.5 Exception 5: A message can contain several packets 88 (Level Crossing information). The identities of the corresponding Level Crossings (variable NID_LX) transmitted in the same message shall be different. (New OpenETCS Requirement Type)

###### 33: 8.4.1.4.6 Exception 6: A message transmitted by a balise group can contain several packets 254 (default balise, loop or RIU information). (New OpenETCS Requirement Type)

###### 34: 8.4.1.4.7 Exception 7: A message transmitted by a balise group can contain several packets 145 (Inhibition of balise group message consistency reaction). (New OpenETCS Requirement Type)

###### 35: 8.4.1.4.8 Exception 8: A message transmitted by a balise group can contain several packets 0 (Virtual Balise Cover marker). (New OpenETCS Requirement Type)

###### 36: 8.4.1.4.9 Exception 9: A message transmitted by a balise group can contain several packets 6 (Virtual Balise Cover order). The identities (pairs of variables NID_VBCMK and NID_C) of the corresponding VBC transmitted in the same message shall be different. (New OpenETCS Requirement Type)

#### 37: 8.4.2 Rules for Eurobalise telegrams (New OpenETCS Requirement Type)
- Gathered Type -> R1

##### 38: 8.4.2.1 The format of the telegram to be transmitted by each balise is as follows: (New OpenETCS Requirement Type)
- Gathered Type -> R1

###### 39: Tabelle (New OpenETCS Requirement Type)
- Gathered Type -> R1

###### 40: Zeile (New OpenETCS Requirement Type)
- Gathered Type -> R1

###### 41 (New OpenETCS Requirement Type)
General Format of Balise Telegram
- Gathered Type -> R1

###### 42: Zeile (New OpenETCS Requirement Type)
- Gathered Type -> R1

###### 43 (New OpenETCS Requirement Type)
Field No.
- Gathered Type -> R1

###### 44 (New OpenETCS Requirement Type)
VARIABLE
- Gathered Type -> R1

###### 45 (New OpenETCS Requirement Type)
Length ( bits)
- Gathered Type -> R1

###### 46 (New OpenETCS Requirement Type)
Remarks
- Gathered Type -> R1

###### 47: Zeile (New OpenETCS Requirement Type)
- Gathered Type -> R1

###### 48 (New OpenETCS Requirement Type)
1
- Gathered Type -> R1

###### 49 (New OpenETCS Requirement Type)
Q_UPDOWN
- Gathered Type -> R1

###### 50 (New OpenETCS Requirement Type)
1
- Gathered Type -> R1

###### 51 (New OpenETCS Requirement Type)
Defines the direction of the information:
Down-link telegram (train to track) (0)
Up-link telegram (track to train) (1)
- Gathered Type -> R1

###### 52: Zeile (New OpenETCS Requirement Type)
- Gathered Type -> R1

###### 53 (New OpenETCS Requirement Type)
2
- Gathered Type -> R1

###### 54 (New OpenETCS Requirement Type)
M_VERSION
- Gathered Type -> R1

###### 55 (New OpenETCS Requirement Type)
7
- Gathered Type -> R1

###### 56 (New OpenETCS Requirement Type)
Version of the ERTMS/ETCS system.
- Gathered Type -> R1

###### 57: Zeile (New OpenETCS Requirement Type)
- Gathered Type -> R1

###### 58 (New OpenETCS Requirement Type)
3
- Gathered Type -> R1

###### 59 (New OpenETCS Requirement Type)
Q_MEDIA
- Gathered Type -> R1

###### 60 (New OpenETCS Requirement Type)
1
- Gathered Type -> R1

###### 61 (New OpenETCS Requirement Type)
Defines the type of media: Balise (0)
- Gathered Type -> R1

###### 62: Zeile (New OpenETCS Requirement Type)
- Gathered Type -> R1

###### 63 (New OpenETCS Requirement Type)
4
- Gathered Type -> R1

###### 64 (New OpenETCS Requirement Type)
N_PIG
- Gathered Type -> R1

###### 65 (New OpenETCS Requirement Type)
3
- Gathered Type -> R1

###### 66 (New OpenETCS Requirement Type)
Position in the group. Defines the position of the balise in the balise group.
- Gathered Type -> R1

###### 67: Zeile (New OpenETCS Requirement Type)
- Gathered Type -> R1

###### 68 (New OpenETCS Requirement Type)
5
- Gathered Type -> R1

###### 69 (New OpenETCS Requirement Type)
N_TOTAL
- Gathered Type -> R1

###### 70 (New OpenETCS Requirement Type)
3
- Gathered Type -> R1

###### 71 (New OpenETCS Requirement Type)
Total number of balises in the balise group
- Gathered Type -> R1

###### 72: Zeile (New OpenETCS Requirement Type)
- Gathered Type -> R1

###### 73 (New OpenETCS Requirement Type)
6
- Gathered Type -> R1

###### 74 (New OpenETCS Requirement Type)
M_DUP
- Gathered Type -> R1

###### 75 (New OpenETCS Requirement Type)
2
- Gathered Type -> R1

###### 76 (New OpenETCS Requirement Type)
Used to indicate whether the information of the balise is a duplicate of the balise before or after this one.
- Gathered Type -> R1

###### 77: Zeile (New OpenETCS Requirement Type)
- Gathered Type -> R1

###### 78 (New OpenETCS Requirement Type)
7
- Gathered Type -> R1

###### 79 (New OpenETCS Requirement Type)
M_MCOUNT
- Gathered Type -> R1

###### 80 (New OpenETCS Requirement Type)
8
- Gathered Type -> R1

###### 81 (New OpenETCS Requirement Type)
Message counter (M_MCOUNT) - 8 bits. To enable detection of a change of balise group message during passage of the balise group.
- Gathered Type -> R1

###### 82: Zeile (New OpenETCS Requirement Type)
- Gathered Type -> R1

###### 83 (New OpenETCS Requirement Type)
8
- Gathered Type -> R1

###### 84 (New OpenETCS Requirement Type)
NID_C
- Gathered Type -> R1

###### 85 (New OpenETCS Requirement Type)
10
- Gathered Type -> R1

###### 86 (New OpenETCS Requirement Type)
Country or region.
- Gathered Type -> R1

###### 87: Zeile (New OpenETCS Requirement Type)
- Gathered Type -> R1

###### 88 (New OpenETCS Requirement Type)
9
- Gathered Type -> R1

###### 89 (New OpenETCS Requirement Type)
NID_BG
- Gathered Type -> R1

###### 90 (New OpenETCS Requirement Type)
14
- Gathered Type -> R1

###### 91 (New OpenETCS Requirement Type)
Identity of the balise group.
- Gathered Type -> R1

###### 92: Zeile (New OpenETCS Requirement Type)
- Gathered Type -> R1

###### 93 (New OpenETCS Requirement Type)
10
- Gathered Type -> R1

###### 94 (New OpenETCS Requirement Type)
Q_LINK
- Gathered Type -> R1

###### 95 (New OpenETCS Requirement Type)
1
- Gathered Type -> R1

###### 96 (New OpenETCS Requirement Type)
Marks the balise group as linked (Q_LINK = 1) or unlinked (Q_LINK = 0)
- Gathered Type -> R1

###### 97: Zeile (New OpenETCS Requirement Type)
- Gathered Type -> R1

###### 98 (New OpenETCS Requirement Type)
- Gathered Type -> R1

###### 99 (New OpenETCS Requirement Type)
Packet 0 (optional)
- Gathered Type -> R1

###### 100 (New OpenETCS Requirement Type)
14
- Gathered Type -> R1

###### 101 (New OpenETCS Requirement Type)
Virtual Balise Cover marker
- Gathered Type -> R1

###### 102: Zeile (New OpenETCS Requirement Type)
- Gathered Type -> R1

###### 103 (New OpenETCS Requirement Type)
- Gathered Type -> R1

###### 104 (New OpenETCS Requirement Type)
Information
- Gathered Type -> R1

###### 105 (New OpenETCS Requirement Type)
Variable
- Gathered Type -> R1

###### 106 (New OpenETCS Requirement Type)
This information is composed according to the rules applicable for packets.
- Gathered Type -> R1

###### 107: Zeile (New OpenETCS Requirement Type)
- Gathered Type -> R1

###### 108 (New OpenETCS Requirement Type)
- Gathered Type -> R1

###### 109 (New OpenETCS Requirement Type)
Packet 255
- Gathered Type -> R1

###### 110 (New OpenETCS Requirement Type)
8
- Gathered Type -> R1

###### 111 (New OpenETCS Requirement Type)
Finishing flag of the telegram
- Gathered Type -> R1

###### 112 (New OpenETCS Requirement Type)
Number of bits in balise header: 50
- Gathered Type -> R1

##### 113: 8.4.2.2 The user information transmitted by a balise shall contain complete packets, i.e. splitting a packet between two balises is forbidden. (New OpenETCS Requirement Type)
- Gathered Type -> R1

##### 114: 8.4.2.3 When used, the packet 0 shall be transmitted as the first packet of the telegram (i.e. it is appended to the header). (New OpenETCS Requirement Type)
- Gathered Type -> R1

#### 115: 8.4.3 Rules for Euroloop messages (New OpenETCS Requirement Type)

##### 116: 8.4.3.1 The format of the message to be transmitted by each loop is as follows: (New OpenETCS Requirement Type)

###### 117: Tabelle (New OpenETCS Requirement Type)

###### 118: Zeile (New OpenETCS Requirement Type)

###### 119 (New OpenETCS Requirement Type)
General Format of Loop Message

###### 120: Zeile (New OpenETCS Requirement Type)

###### 121 (New OpenETCS Requirement Type)
Field No.

###### 122 (New OpenETCS Requirement Type)
VARIABLE

###### 123 (New OpenETCS Requirement Type)
Length ( bits)

###### 124 (New OpenETCS Requirement Type)
Remarks

###### 125: Zeile (New OpenETCS Requirement Type)

###### 126 (New OpenETCS Requirement Type)
1

###### 127 (New OpenETCS Requirement Type)
Q_UPDOWN

###### 128 (New OpenETCS Requirement Type)
1

###### 129 (New OpenETCS Requirement Type)
Defines the direction of the information:
Down-link message (train to track) (0)
Up-link message (track to train) (1)

###### 130: Zeile (New OpenETCS Requirement Type)

###### 131 (New OpenETCS Requirement Type)
2

###### 132 (New OpenETCS Requirement Type)
M_VERSION

###### 133 (New OpenETCS Requirement Type)
7

###### 134 (New OpenETCS Requirement Type)
Version of the ERTMS/ETCS system.

###### 135: Zeile (New OpenETCS Requirement Type)

###### 136 (New OpenETCS Requirement Type)
3

###### 137 (New OpenETCS Requirement Type)
Q_MEDIA

###### 138 (New OpenETCS Requirement Type)
1

###### 139 (New OpenETCS Requirement Type)
Defines the type of media: Loop (1)

###### 140: Zeile (New OpenETCS Requirement Type)

###### 141 (New OpenETCS Requirement Type)
4

###### 142 (New OpenETCS Requirement Type)
NID_C

###### 143 (New OpenETCS Requirement Type)
10

###### 144 (New OpenETCS Requirement Type)
Country or region.

###### 145: Zeile (New OpenETCS Requirement Type)

###### 146 (New OpenETCS Requirement Type)
5

###### 147 (New OpenETCS Requirement Type)
NID_LOOP

###### 148 (New OpenETCS Requirement Type)
14

###### 149 (New OpenETCS Requirement Type)
Identity of Euroloop.

###### 150: Zeile (New OpenETCS Requirement Type)

###### 151 (New OpenETCS Requirement Type)

###### 152 (New OpenETCS Requirement Type)

###### 153 (New OpenETCS Requirement Type)

###### 154 (New OpenETCS Requirement Type)

###### 155: Zeile (New OpenETCS Requirement Type)

###### 156 (New OpenETCS Requirement Type)

###### 157 (New OpenETCS Requirement Type)

###### 158 (New OpenETCS Requirement Type)

###### 159 (New OpenETCS Requirement Type)

###### 160: Zeile (New OpenETCS Requirement Type)

###### 161 (New OpenETCS Requirement Type)

###### 162 (New OpenETCS Requirement Type)
Information

###### 163 (New OpenETCS Requirement Type)
Variable

###### 164 (New OpenETCS Requirement Type)
This information is composed according to the rules applicable for packets.

###### 165: Zeile (New OpenETCS Requirement Type)

###### 166 (New OpenETCS Requirement Type)

###### 167 (New OpenETCS Requirement Type)
Packet 255

###### 168 (New OpenETCS Requirement Type)
8

###### 169 (New OpenETCS Requirement Type)
Finishing flag of the message

###### 170 (New OpenETCS Requirement Type)
Number of bits in loop header: 33

##### 171: 8.4.3.2 Intentionally deleted. (New OpenETCS Requirement Type)

#### 172: 8.4.4 Rules for Euroradio messages (New OpenETCS Requirement Type)

##### 173: 8.4.4.1 The message identifier is unique (variable NID_MESSAGE). (New OpenETCS Requirement Type)

###### 174: 8.4.4.1.1 All currently not defined message identifiers are reserved for future use and shall be considered as invalid values (i.e. like spare values). Exception: reception of information only differing by Y with regards to the highest system version number X supported by on-board (refer to section 3.17.3.11 b)). (New OpenETCS Requirement Type)

##### 175: 8.4.4.2 Each message shall indicate its own length through the use of the variable L_MESSAGE. (New OpenETCS Requirement Type)

###### 176: 8.4.4.2.1 If the computed length of the message is not equal to the length given by L_MESSAGE, the entire message shall be rejected. (New OpenETCS Requirement Type)

##### 177: 8.4.4.3 The messages shall be composed of predefined variables and packets. (New OpenETCS Requirement Type)

##### 178: 8.4.4.4 For some messages, it shall be possible to add optional packets at the end of the message. (New OpenETCS Requirement Type)

###### 179: 8.4.4.4.1 The track to train messages possibly including optional packets are listed hereafter: (New OpenETCS Requirement Type)

###### 180: Tabelle (New OpenETCS Requirement Type)

###### 181: Zeile (New OpenETCS Requirement Type)

###### 182 (New OpenETCS Requirement Type)
Track to Train message

###### 183 (New OpenETCS Requirement Type)
Mess. ID

###### 184 (New OpenETCS Requirement Type)
Optional packets

###### 185: Zeile (New OpenETCS Requirement Type)

###### 186 (New OpenETCS Requirement Type)
SR Authorisation

###### 187 (New OpenETCS Requirement Type)
2

###### 188 (New OpenETCS Requirement Type)
63

###### 189: Zeile (New OpenETCS Requirement Type)

###### 190 (New OpenETCS Requirement Type)
Movement Authority

###### 191 (New OpenETCS Requirement Type)
3

###### 192 (New OpenETCS Requirement Type)
21, 27, 49, 80, plus common optional packets

###### 193: Zeile (New OpenETCS Requirement Type)

###### 194 (New OpenETCS Requirement Type)
Request To Shorten MA

###### 195 (New OpenETCS Requirement Type)
9

###### 196 (New OpenETCS Requirement Type)
49, 80

###### 197: Zeile (New OpenETCS Requirement Type)

###### 198 (New OpenETCS Requirement Type)
General Message

###### 199 (New OpenETCS Requirement Type)
24

###### 200 (New OpenETCS Requirement Type)
From RBC: 21, 27, plus common optional packets
From RIU: 45, 143, 254

###### 201: Zeile (New OpenETCS Requirement Type)

###### 202 (New OpenETCS Requirement Type)
SH authorised

###### 203 (New OpenETCS Requirement Type)
28

###### 204 (New OpenETCS Requirement Type)
3, 44, 49

###### 205: Zeile (New OpenETCS Requirement Type)

###### 206 (New OpenETCS Requirement Type)
MA with Shifted Location Reference

###### 207 (New OpenETCS Requirement Type)
33

###### 208 (New OpenETCS Requirement Type)
21, 27, 49, 80, plus common optional packets

###### 209: Zeile (New OpenETCS Requirement Type)

###### 210 (New OpenETCS Requirement Type)
Infill MA

###### 211 (New OpenETCS Requirement Type)
37

###### 212 (New OpenETCS Requirement Type)
5, 21, 27, 39, 40, 41, 44, 49, 51, 65, 66, 68, 69, 70, 71, 80, 88, 138, 139

###### 213: 8.4.4.4.1.1 The common optional packets are the following ones: (New OpenETCS Requirement Type)

###### 214: Tabelle (New OpenETCS Requirement Type)

###### 215: Zeile (New OpenETCS Requirement Type)

###### 216 (New OpenETCS Requirement Type)
Common optional packets

###### 217: Zeile (New OpenETCS Requirement Type)

###### 218 (New OpenETCS Requirement Type)
3, 5, 39, 40, 51, 41, 42, 44, 45, 52, 57, 58, 64, 65, 66, 68, 69, 70, 71, 72, 76, 79, 88, 131, 138, 139, 140

###### 219: 8.4.4.4.2 The train to track message 136 (Train Position Report) and 157 (SoM Position Report) may optionally include the following packets: (New OpenETCS Requirement Type)

###### 220: Packet 4 (Error Reporting), (New OpenETCS Requirement Type)

###### 221: Packet 5 (Train running number), (New OpenETCS Requirement Type)

###### 222: Packet 44 (Data used by applications outside the ERTMS/ETCS system). (New OpenETCS Requirement Type)

###### 223: 8.4.4.4.3 The train to track message 159 (Session Established) may optionally include the following packets: (New OpenETCS Requirement Type)

###### 224 (New OpenETCS Requirement Type)
Packet 3 (Onboard Telephone Numbers)

###### 225: 8.4.4.4.4 The train to track message 132 (MA request) may optionally include the following packet: (New OpenETCS Requirement Type)

###### 226: a) Packet 9 (Level 2/3 transition information) (New OpenETCS Requirement Type)

##### 227: 8.4.4.5 If needed to obtain an integer number of bytes, padding shall be added at the end of the message. (New OpenETCS Requirement Type)

##### 228: 8.4.4.6 Standard format of a radio message from track to train : (New OpenETCS Requirement Type)

###### 229: 8.4.4.6.1 Format: (New OpenETCS Requirement Type)

###### 230: Tabelle (New OpenETCS Requirement Type)

###### 231: Zeile (New OpenETCS Requirement Type)

###### 232 (New OpenETCS Requirement Type)
Field No.

###### 233 (New OpenETCS Requirement Type)
VARIABLE

###### 234 (New OpenETCS Requirement Type)
Remarks

###### 235: Zeile (New OpenETCS Requirement Type)

###### 236 (New OpenETCS Requirement Type)

###### 237 (New OpenETCS Requirement Type)
NID_MESSAGE

###### 238 (New OpenETCS Requirement Type)
Message Identification Number

###### 239: Zeile (New OpenETCS Requirement Type)

###### 240 (New OpenETCS Requirement Type)

###### 241 (New OpenETCS Requirement Type)
L_MESSAGE

###### 242 (New OpenETCS Requirement Type)
Message length including everything (from field 1 to padding inclusive).

###### 243: Zeile (New OpenETCS Requirement Type)

###### 244 (New OpenETCS Requirement Type)

###### 245 (New OpenETCS Requirement Type)
T_TRAIN

###### 246 (New OpenETCS Requirement Type)
Time Stamp from RBC (see sections 3.16.3.2 & 3.16.3.3).

###### 247: Zeile (New OpenETCS Requirement Type)

###### 248 (New OpenETCS Requirement Type)

###### 249 (New OpenETCS Requirement Type)
M_ACK

###### 250 (New OpenETCS Requirement Type)
Indicates whether the message must be acknowledged (or not) by the on-board equipment (message n° 146).

###### 251: Zeile (New OpenETCS Requirement Type)

###### 252 (New OpenETCS Requirement Type)

###### 253 (New OpenETCS Requirement Type)
NID_LRBG

###### 254 (New OpenETCS Requirement Type)
Identification Number of LRBG.

###### 255: Zeile (New OpenETCS Requirement Type)

###### 256 (New OpenETCS Requirement Type)
…

###### 257 (New OpenETCS Requirement Type)
variables as required by NID_MESSAGE

###### 258 (New OpenETCS Requirement Type)
If needed for this message. Used when sending variables which are not included in a packet.

###### 259: Zeile (New OpenETCS Requirement Type)

###### 260 (New OpenETCS Requirement Type)
…

###### 261 (New OpenETCS Requirement Type)
packets as required by NID_MESSAGE

###### 262 (New OpenETCS Requirement Type)
If needed for this message.

###### 263: Zeile (New OpenETCS Requirement Type)

###### 264 (New OpenETCS Requirement Type)

###### 265 (New OpenETCS Requirement Type)
Optional packets

###### 266 (New OpenETCS Requirement Type)
Refer to section 8.4.4.4 of this document.

###### 267: Zeile (New OpenETCS Requirement Type)

###### 268 (New OpenETCS Requirement Type)

###### 269 (New OpenETCS Requirement Type)
Padding

###### 270 (New OpenETCS Requirement Type)
If required.

###### 271: 8.4.4.6.2 Note: In section 8.7 giving the contents of the messages, the padding information is intentionally omitted. (New OpenETCS Requirement Type)

###### 272: 8.4.4.6.3 The track to train message 39 (Acknowledgement of termination of a communication session) shall include the variable M_ACK set to 0. Justification: see 3.5.5.3. (New OpenETCS Requirement Type)

##### 273: 8.4.4.7 Standard format of a radio message from train to track: (New OpenETCS Requirement Type)

###### 274: 8.4.4.7.1 Format: (New OpenETCS Requirement Type)

###### 275: Tabelle (New OpenETCS Requirement Type)

###### 276: Zeile (New OpenETCS Requirement Type)

###### 277 (New OpenETCS Requirement Type)
Field No.

###### 278 (New OpenETCS Requirement Type)
VARIABLE

###### 279 (New OpenETCS Requirement Type)
Remarks

###### 280: Zeile (New OpenETCS Requirement Type)

###### 281 (New OpenETCS Requirement Type)

###### 282 (New OpenETCS Requirement Type)
NID_MESSAGE

###### 283 (New OpenETCS Requirement Type)
Message Identification Number

###### 284: Zeile (New OpenETCS Requirement Type)

###### 285 (New OpenETCS Requirement Type)

###### 286 (New OpenETCS Requirement Type)
L_MESSAGE

###### 287 (New OpenETCS Requirement Type)
Message length including everything (from field 1 to padding inclusive).

###### 288: Zeile (New OpenETCS Requirement Type)

###### 289 (New OpenETCS Requirement Type)

###### 290 (New OpenETCS Requirement Type)
T_TRAIN

###### 291 (New OpenETCS Requirement Type)
Time Stamp from Train (see chapter 3 – Data Consistency).

###### 292: Zeile (New OpenETCS Requirement Type)

###### 293 (New OpenETCS Requirement Type)

###### 294 (New OpenETCS Requirement Type)
NID_ENGINE

###### 295 (New OpenETCS Requirement Type)
Identity of the train.

###### 296: Zeile (New OpenETCS Requirement Type)

###### 297 (New OpenETCS Requirement Type)

###### 298 (New OpenETCS Requirement Type)
variables as required by NID_MESSAGE

###### 299 (New OpenETCS Requirement Type)
If needed for this message. Used when sending variables which are not included in a packet.

###### 300: Zeile (New OpenETCS Requirement Type)

###### 301 (New OpenETCS Requirement Type)

###### 302 (New OpenETCS Requirement Type)
Packet 0 or 1

###### 303 (New OpenETCS Requirement Type)
Train-to-track packet type 0 – Position report, or packet type 1 - Position report based on two balise groups. Not included in messages 146, 154, 155, 156 and 159.

###### 304: Zeile (New OpenETCS Requirement Type)

###### 305 (New OpenETCS Requirement Type)

###### 306 (New OpenETCS Requirement Type)
Other Packets as required by NID_MESSAGE

###### 307 (New OpenETCS Requirement Type)
(only for message 129)

###### 308: Zeile (New OpenETCS Requirement Type)

###### 309 (New OpenETCS Requirement Type)

###### 310 (New OpenETCS Requirement Type)
Optional packets

###### 311 (New OpenETCS Requirement Type)

###### 312: Zeile (New OpenETCS Requirement Type)

###### 313 (New OpenETCS Requirement Type)

###### 314 (New OpenETCS Requirement Type)
Padding

###### 315 (New OpenETCS Requirement Type)
If required.

###### 316: 8.4.4.7.2 Exception: The position report (packet 0 or packet 1) shall not be included in the following messages: (New OpenETCS Requirement Type)

###### 317: Message 146 (Acknowledgement), (New OpenETCS Requirement Type)

###### 318: Message 154 (No compatible version supported), (New OpenETCS Requirement Type)

###### 319: Message 155 (Initiation of a communication session), (New OpenETCS Requirement Type)

###### 320: Message 156 (Termination of a communication session), (New OpenETCS Requirement Type)

###### 321: Intentionally deleted (New OpenETCS Requirement Type)

###### 322: Message 159 (Session Established). (New OpenETCS Requirement Type)

###### 323: 8.4.4.7.3 Note: In section 8.6 giving the contents of the messages, the padding information is intentionally omitted. (New OpenETCS Requirement Type)

### 324: 8.5 List of radio Messages (New OpenETCS Requirement Type)

#### 325: 8.5.1 Introduction (New OpenETCS Requirement Type)

##### 326: 8.5.1.1 This section identifies the radio messages with corresponding Message Identifier (“Mes. Id.”) and Message Name. It also gives a list of the version-invariant messages. (New OpenETCS Requirement Type)

##### 327: 8.5.1.2 “Type” defines whether a message is to be sent as normal priority (N) or as high priority data (E), as defined in Euroradio specifications. (New OpenETCS Requirement Type)

#### 328: 8.5.2 Train to Track radio messages (New OpenETCS Requirement Type)

##### 329: Tabelle (New OpenETCS Requirement Type)

###### 330: Zeile (New OpenETCS Requirement Type)

###### 331 (New OpenETCS Requirement Type)
Mes. Id.

###### 332 (New OpenETCS Requirement Type)
Message Name

###### 333 (New OpenETCS Requirement Type)
Type

###### 334 (New OpenETCS Requirement Type)
Invariant

###### 335 (New OpenETCS Requirement Type)
Transmitted to

###### 336: Zeile (New OpenETCS Requirement Type)

###### 337 (New OpenETCS Requirement Type)
129

###### 338 (New OpenETCS Requirement Type)
Validated Train Data

###### 339 (New OpenETCS Requirement Type)
N

###### 340 (New OpenETCS Requirement Type)
No

###### 341 (New OpenETCS Requirement Type)
RBC

###### 342: Zeile (New OpenETCS Requirement Type)

###### 343 (New OpenETCS Requirement Type)
130

###### 344 (New OpenETCS Requirement Type)
Request for Shunting

###### 345 (New OpenETCS Requirement Type)
N

###### 346 (New OpenETCS Requirement Type)
No

###### 347 (New OpenETCS Requirement Type)
RBC

###### 348: Zeile (New OpenETCS Requirement Type)

###### 349 (New OpenETCS Requirement Type)
132

###### 350 (New OpenETCS Requirement Type)
MA Request

###### 351 (New OpenETCS Requirement Type)
N

###### 352 (New OpenETCS Requirement Type)
No

###### 353 (New OpenETCS Requirement Type)
RBC

###### 354: Zeile (New OpenETCS Requirement Type)

###### 355 (New OpenETCS Requirement Type)
136

###### 356 (New OpenETCS Requirement Type)
Train Position Report

###### 357 (New OpenETCS Requirement Type)
N

###### 358 (New OpenETCS Requirement Type)
No

###### 359 (New OpenETCS Requirement Type)
RBC, RIU

###### 360: Zeile (New OpenETCS Requirement Type)

###### 361 (New OpenETCS Requirement Type)
137

###### 362 (New OpenETCS Requirement Type)
Request to shorten MA is granted

###### 363 (New OpenETCS Requirement Type)
N

###### 364 (New OpenETCS Requirement Type)
No

###### 365 (New OpenETCS Requirement Type)
RBC

###### 366: Zeile (New OpenETCS Requirement Type)

###### 367 (New OpenETCS Requirement Type)
138

###### 368 (New OpenETCS Requirement Type)
Request to shorten MA is rejected

###### 369 (New OpenETCS Requirement Type)
N

###### 370 (New OpenETCS Requirement Type)
No

###### 371 (New OpenETCS Requirement Type)
RBC

###### 372: Zeile (New OpenETCS Requirement Type)

###### 373 (New OpenETCS Requirement Type)
146

###### 374 (New OpenETCS Requirement Type)
Acknowledgement

###### 375 (New OpenETCS Requirement Type)
N

###### 376 (New OpenETCS Requirement Type)
No

###### 377 (New OpenETCS Requirement Type)
RBC, RIU

###### 378: Zeile (New OpenETCS Requirement Type)

###### 379 (New OpenETCS Requirement Type)
147

###### 380 (New OpenETCS Requirement Type)
Acknowledgement of Emergency Stop

###### 381 (New OpenETCS Requirement Type)
N

###### 382 (New OpenETCS Requirement Type)
No

###### 383 (New OpenETCS Requirement Type)
RBC

###### 384: Zeile (New OpenETCS Requirement Type)

###### 385 (New OpenETCS Requirement Type)
149

###### 386 (New OpenETCS Requirement Type)
Track Ahead Free Granted

###### 387 (New OpenETCS Requirement Type)
N

###### 388 (New OpenETCS Requirement Type)
No

###### 389 (New OpenETCS Requirement Type)
RBC

###### 390: Zeile (New OpenETCS Requirement Type)

###### 391 (New OpenETCS Requirement Type)
150

###### 392 (New OpenETCS Requirement Type)
End of Mission

###### 393 (New OpenETCS Requirement Type)
N

###### 394 (New OpenETCS Requirement Type)
No

###### 395 (New OpenETCS Requirement Type)
RBC

###### 396: Zeile (New OpenETCS Requirement Type)

###### 397 (New OpenETCS Requirement Type)
153

###### 398 (New OpenETCS Requirement Type)
Radio infill request

###### 399 (New OpenETCS Requirement Type)
N

###### 400 (New OpenETCS Requirement Type)
No

###### 401 (New OpenETCS Requirement Type)
RIU

###### 402: Zeile (New OpenETCS Requirement Type)

###### 403 (New OpenETCS Requirement Type)
154

###### 404 (New OpenETCS Requirement Type)
No compatible version supported

###### 405 (New OpenETCS Requirement Type)
N

###### 406 (New OpenETCS Requirement Type)
Yes

###### 407 (New OpenETCS Requirement Type)
RBC, RIU

###### 408: Zeile (New OpenETCS Requirement Type)

###### 409 (New OpenETCS Requirement Type)
155

###### 410 (New OpenETCS Requirement Type)
Initiation of a communication session

###### 411 (New OpenETCS Requirement Type)
N

###### 412 (New OpenETCS Requirement Type)
Yes

###### 413 (New OpenETCS Requirement Type)
RBC, RIU

###### 414: Zeile (New OpenETCS Requirement Type)

###### 415 (New OpenETCS Requirement Type)
156

###### 416 (New OpenETCS Requirement Type)
Termination of a communication session

###### 417 (New OpenETCS Requirement Type)
N

###### 418 (New OpenETCS Requirement Type)
Yes

###### 419 (New OpenETCS Requirement Type)
RBC, RIU

###### 420: Zeile (New OpenETCS Requirement Type)

###### 421 (New OpenETCS Requirement Type)
157

###### 422 (New OpenETCS Requirement Type)
SoM Position Report

###### 423 (New OpenETCS Requirement Type)
N

###### 424 (New OpenETCS Requirement Type)
No

###### 425 (New OpenETCS Requirement Type)
RBC

###### 426: Zeile (New OpenETCS Requirement Type)

###### 427 (New OpenETCS Requirement Type)
158

###### 428 (New OpenETCS Requirement Type)
Text message acknowledged by driver

###### 429 (New OpenETCS Requirement Type)
N

###### 430 (New OpenETCS Requirement Type)
No

###### 431 (New OpenETCS Requirement Type)
RBC

###### 432: Zeile (New OpenETCS Requirement Type)

###### 433 (New OpenETCS Requirement Type)
159

###### 434 (New OpenETCS Requirement Type)
Session Established

###### 435 (New OpenETCS Requirement Type)
N

###### 436 (New OpenETCS Requirement Type)
No

###### 437 (New OpenETCS Requirement Type)
RBC, RIU

#### 438: 8.5.3 Track to Train radio messages (New OpenETCS Requirement Type)

##### 439: Tabelle (New OpenETCS Requirement Type)

###### 440: Zeile (New OpenETCS Requirement Type)

###### 441 (New OpenETCS Requirement Type)
Mes. Id.

###### 442 (New OpenETCS Requirement Type)
Message Name

###### 443 (New OpenETCS Requirement Type)
Type

###### 444 (New OpenETCS Requirement Type)
Invariant

###### 445 (New OpenETCS Requirement Type)
Transmitted by

###### 446: Zeile (New OpenETCS Requirement Type)

###### 447 (New OpenETCS Requirement Type)
2

###### 448 (New OpenETCS Requirement Type)
SR Authorisation

###### 449 (New OpenETCS Requirement Type)
N

###### 450 (New OpenETCS Requirement Type)
No

###### 451 (New OpenETCS Requirement Type)
RBC

###### 452: Zeile (New OpenETCS Requirement Type)

###### 453 (New OpenETCS Requirement Type)
3

###### 454 (New OpenETCS Requirement Type)
Movement Authority

###### 455 (New OpenETCS Requirement Type)
N

###### 456 (New OpenETCS Requirement Type)
No

###### 457 (New OpenETCS Requirement Type)
RBC

###### 458: Zeile (New OpenETCS Requirement Type)

###### 459 (New OpenETCS Requirement Type)
6

###### 460 (New OpenETCS Requirement Type)
Recognition of exit from TRIP mode

###### 461 (New OpenETCS Requirement Type)
N

###### 462 (New OpenETCS Requirement Type)
No

###### 463 (New OpenETCS Requirement Type)
RBC

###### 464: Zeile (New OpenETCS Requirement Type)

###### 465 (New OpenETCS Requirement Type)
8

###### 466 (New OpenETCS Requirement Type)
Acknowledgement of Train Data

###### 467 (New OpenETCS Requirement Type)
N

###### 468 (New OpenETCS Requirement Type)
No

###### 469 (New OpenETCS Requirement Type)
RBC

###### 470: Zeile (New OpenETCS Requirement Type)

###### 471 (New OpenETCS Requirement Type)
9

###### 472 (New OpenETCS Requirement Type)
Request to Shorten MA

###### 473 (New OpenETCS Requirement Type)
N

###### 474 (New OpenETCS Requirement Type)
No

###### 475 (New OpenETCS Requirement Type)
RBC

###### 476: Zeile (New OpenETCS Requirement Type)

###### 477 (New OpenETCS Requirement Type)
15

###### 478 (New OpenETCS Requirement Type)
Conditional Emergency Stop

###### 479 (New OpenETCS Requirement Type)
E or N

###### 480 (New OpenETCS Requirement Type)
No

###### 481 (New OpenETCS Requirement Type)
RBC

###### 482: Zeile (New OpenETCS Requirement Type)

###### 483 (New OpenETCS Requirement Type)
16

###### 484 (New OpenETCS Requirement Type)
Unconditional Emergency Stop

###### 485 (New OpenETCS Requirement Type)
E or N

###### 486 (New OpenETCS Requirement Type)
No

###### 487 (New OpenETCS Requirement Type)
RBC

###### 488: Zeile (New OpenETCS Requirement Type)

###### 489 (New OpenETCS Requirement Type)
18

###### 490 (New OpenETCS Requirement Type)
Revocation of Emergency Stop

###### 491 (New OpenETCS Requirement Type)
N

###### 492 (New OpenETCS Requirement Type)
No

###### 493 (New OpenETCS Requirement Type)
RBC

###### 494: Zeile (New OpenETCS Requirement Type)

###### 495 (New OpenETCS Requirement Type)
24

###### 496 (New OpenETCS Requirement Type)
General message

###### 497 (New OpenETCS Requirement Type)
N

###### 498 (New OpenETCS Requirement Type)
No

###### 499 (New OpenETCS Requirement Type)
RBC, RIU

###### 500: Zeile (New OpenETCS Requirement Type)

###### 501 (New OpenETCS Requirement Type)
27

###### 502 (New OpenETCS Requirement Type)
SH Refused

###### 503 (New OpenETCS Requirement Type)
N

###### 504 (New OpenETCS Requirement Type)
No

###### 505 (New OpenETCS Requirement Type)
RBC

###### 506: Zeile (New OpenETCS Requirement Type)

###### 507 (New OpenETCS Requirement Type)
28

###### 508 (New OpenETCS Requirement Type)
SH Authorised

###### 509 (New OpenETCS Requirement Type)
N

###### 510 (New OpenETCS Requirement Type)
No

###### 511 (New OpenETCS Requirement Type)
RBC

###### 512: Zeile (New OpenETCS Requirement Type)

###### 513 (New OpenETCS Requirement Type)
33

###### 514 (New OpenETCS Requirement Type)
MA with Shifted Location Reference

###### 515 (New OpenETCS Requirement Type)
N

###### 516 (New OpenETCS Requirement Type)
No

###### 517 (New OpenETCS Requirement Type)
RBC

###### 518: Zeile (New OpenETCS Requirement Type)

###### 519 (New OpenETCS Requirement Type)
34

###### 520 (New OpenETCS Requirement Type)
Track Ahead Free Request

###### 521 (New OpenETCS Requirement Type)
N

###### 522 (New OpenETCS Requirement Type)
No

###### 523 (New OpenETCS Requirement Type)
RBC

###### 524: Zeile (New OpenETCS Requirement Type)

###### 525 (New OpenETCS Requirement Type)
37

###### 526 (New OpenETCS Requirement Type)
Infill MA

###### 527 (New OpenETCS Requirement Type)
N

###### 528 (New OpenETCS Requirement Type)
No

###### 529 (New OpenETCS Requirement Type)
RIU

###### 530: Zeile (New OpenETCS Requirement Type)

###### 531 (New OpenETCS Requirement Type)
40

###### 532 (New OpenETCS Requirement Type)
Train Rejected

###### 533 (New OpenETCS Requirement Type)
N

###### 534 (New OpenETCS Requirement Type)
No

###### 535 (New OpenETCS Requirement Type)
RBC

###### 536: Zeile (New OpenETCS Requirement Type)

###### 537 (New OpenETCS Requirement Type)
32

###### 538 (New OpenETCS Requirement Type)
RBC/RIU System Version

###### 539 (New OpenETCS Requirement Type)
N

###### 540 (New OpenETCS Requirement Type)
Yes

###### 541 (New OpenETCS Requirement Type)
RBC, RIU

###### 542: Zeile (New OpenETCS Requirement Type)

###### 543 (New OpenETCS Requirement Type)
38

###### 544 (New OpenETCS Requirement Type)
Initiation of a communication session

###### 545 (New OpenETCS Requirement Type)
N

###### 546 (New OpenETCS Requirement Type)
Yes

###### 547 (New OpenETCS Requirement Type)
RBC

###### 548: Zeile (New OpenETCS Requirement Type)

###### 549 (New OpenETCS Requirement Type)
39

###### 550 (New OpenETCS Requirement Type)
Acknowledgement of termination of a communication session

###### 551 (New OpenETCS Requirement Type)
N

###### 552 (New OpenETCS Requirement Type)
Yes

###### 553 (New OpenETCS Requirement Type)
RBC, RIU

###### 554: Zeile (New OpenETCS Requirement Type)

###### 555 (New OpenETCS Requirement Type)
41

###### 556 (New OpenETCS Requirement Type)
Train Accepted

###### 557 (New OpenETCS Requirement Type)
N

###### 558 (New OpenETCS Requirement Type)
No

###### 559 (New OpenETCS Requirement Type)
RBC

###### 560: Zeile (New OpenETCS Requirement Type)

###### 561 (New OpenETCS Requirement Type)
43

###### 562 (New OpenETCS Requirement Type)
SoM position report confirmed by RBC

###### 563 (New OpenETCS Requirement Type)
N

###### 564 (New OpenETCS Requirement Type)
No

###### 565 (New OpenETCS Requirement Type)
RBC

###### 566: Zeile (New OpenETCS Requirement Type)

###### 567 (New OpenETCS Requirement Type)
45

###### 568 (New OpenETCS Requirement Type)
Assignment of coordinate system

###### 569 (New OpenETCS Requirement Type)
N

###### 570 (New OpenETCS Requirement Type)
No

###### 571 (New OpenETCS Requirement Type)
RBC

### 572: 8.6 Definition of Radio Messages from Train to Track (New OpenETCS Requirement Type)

#### 573: 8.6.1 Message 129: Validated Train Data (New OpenETCS Requirement Type)

##### 574: Tabelle (New OpenETCS Requirement Type)

###### 575: Zeile (New OpenETCS Requirement Type)

###### 576 (New OpenETCS Requirement Type)
Field No.

###### 577 (New OpenETCS Requirement Type)
VARIABLE/ PACKET

###### 578 (New OpenETCS Requirement Type)
Remarks

###### 579: Zeile (New OpenETCS Requirement Type)

###### 580 (New OpenETCS Requirement Type)

###### 581 (New OpenETCS Requirement Type)
NID_MESSAGE

###### 582 (New OpenETCS Requirement Type)

###### 583: Zeile (New OpenETCS Requirement Type)

###### 584 (New OpenETCS Requirement Type)

###### 585 (New OpenETCS Requirement Type)
L_MESSAGE

###### 586 (New OpenETCS Requirement Type)

###### 587: Zeile (New OpenETCS Requirement Type)

###### 588 (New OpenETCS Requirement Type)

###### 589 (New OpenETCS Requirement Type)
T_TRAIN

###### 590 (New OpenETCS Requirement Type)

###### 591: Zeile (New OpenETCS Requirement Type)

###### 592 (New OpenETCS Requirement Type)

###### 593 (New OpenETCS Requirement Type)
NID_ENGINE

###### 594 (New OpenETCS Requirement Type)

###### 595: Zeile (New OpenETCS Requirement Type)

###### 596 (New OpenETCS Requirement Type)

###### 597 (New OpenETCS Requirement Type)
Packet 0 or 1

###### 598 (New OpenETCS Requirement Type)

###### 599: Zeile (New OpenETCS Requirement Type)

###### 600 (New OpenETCS Requirement Type)

###### 601 (New OpenETCS Requirement Type)
Train data

###### 602 (New OpenETCS Requirement Type)
Train - track packet type 11.

#### 603: 8.6.2 Message 130: Request for Shunting (New OpenETCS Requirement Type)

##### 604: Tabelle (New OpenETCS Requirement Type)

###### 605: Zeile (New OpenETCS Requirement Type)

###### 606 (New OpenETCS Requirement Type)
Field No.

###### 607 (New OpenETCS Requirement Type)
VARIABLE/ PACKET

###### 608 (New OpenETCS Requirement Type)
Remarks

###### 609: Zeile (New OpenETCS Requirement Type)

###### 610 (New OpenETCS Requirement Type)

###### 611 (New OpenETCS Requirement Type)
NID_MESSAGE

###### 612 (New OpenETCS Requirement Type)

###### 613: Zeile (New OpenETCS Requirement Type)

###### 614 (New OpenETCS Requirement Type)

###### 615 (New OpenETCS Requirement Type)
L_MESSAGE

###### 616 (New OpenETCS Requirement Type)

###### 617: Zeile (New OpenETCS Requirement Type)

###### 618 (New OpenETCS Requirement Type)

###### 619 (New OpenETCS Requirement Type)
T_TRAIN

###### 620 (New OpenETCS Requirement Type)

###### 621: Zeile (New OpenETCS Requirement Type)

###### 622 (New OpenETCS Requirement Type)

###### 623 (New OpenETCS Requirement Type)
NID_ENGINE

###### 624 (New OpenETCS Requirement Type)

###### 625: Zeile (New OpenETCS Requirement Type)

###### 626 (New OpenETCS Requirement Type)

###### 627 (New OpenETCS Requirement Type)
Packet 0 or 1

###### 628 (New OpenETCS Requirement Type)

#### 629: 8.6.3 Message 132: MA Request (New OpenETCS Requirement Type)

##### 630: Tabelle (New OpenETCS Requirement Type)

###### 631: Zeile (New OpenETCS Requirement Type)

###### 632 (New OpenETCS Requirement Type)
Field No.

###### 633 (New OpenETCS Requirement Type)
VARIABLE/ PACKET

###### 634 (New OpenETCS Requirement Type)
Remarks

###### 635: Zeile (New OpenETCS Requirement Type)

###### 636 (New OpenETCS Requirement Type)

###### 637 (New OpenETCS Requirement Type)
NID_MESSAGE

###### 638 (New OpenETCS Requirement Type)

###### 639: Zeile (New OpenETCS Requirement Type)

###### 640 (New OpenETCS Requirement Type)

###### 641 (New OpenETCS Requirement Type)
L_MESSAGE

###### 642 (New OpenETCS Requirement Type)

###### 643: Zeile (New OpenETCS Requirement Type)

###### 644 (New OpenETCS Requirement Type)

###### 645 (New OpenETCS Requirement Type)
T_TRAIN

###### 646 (New OpenETCS Requirement Type)

###### 647: Zeile (New OpenETCS Requirement Type)

###### 648 (New OpenETCS Requirement Type)

###### 649 (New OpenETCS Requirement Type)
NID_ENGINE

###### 650 (New OpenETCS Requirement Type)

###### 651: Zeile (New OpenETCS Requirement Type)

###### 652 (New OpenETCS Requirement Type)

###### 653 (New OpenETCS Requirement Type)
Q_MARQSTREASON

###### 654 (New OpenETCS Requirement Type)

###### 655: Zeile (New OpenETCS Requirement Type)

###### 656 (New OpenETCS Requirement Type)

###### 657 (New OpenETCS Requirement Type)
Packet 0 or 1

###### 658 (New OpenETCS Requirement Type)

###### 659: Zeile (New OpenETCS Requirement Type)

###### 660 (New OpenETCS Requirement Type)

###### 661 (New OpenETCS Requirement Type)
Optional packets

###### 662 (New OpenETCS Requirement Type)

#### 663: 8.6.4 Message 136: Train Position Report (New OpenETCS Requirement Type)

##### 664: Tabelle (New OpenETCS Requirement Type)

###### 665: Zeile (New OpenETCS Requirement Type)

###### 666 (New OpenETCS Requirement Type)
Field No.

###### 667 (New OpenETCS Requirement Type)
VARIABLE/ PACKET

###### 668 (New OpenETCS Requirement Type)
Remarks

###### 669: Zeile (New OpenETCS Requirement Type)

###### 670 (New OpenETCS Requirement Type)

###### 671 (New OpenETCS Requirement Type)
NID_MESSAGE

###### 672 (New OpenETCS Requirement Type)

###### 673: Zeile (New OpenETCS Requirement Type)

###### 674 (New OpenETCS Requirement Type)

###### 675 (New OpenETCS Requirement Type)
L_MESSAGE

###### 676 (New OpenETCS Requirement Type)

###### 677: Zeile (New OpenETCS Requirement Type)

###### 678 (New OpenETCS Requirement Type)

###### 679 (New OpenETCS Requirement Type)
T_TRAIN

###### 680 (New OpenETCS Requirement Type)

###### 681: Zeile (New OpenETCS Requirement Type)

###### 682 (New OpenETCS Requirement Type)

###### 683 (New OpenETCS Requirement Type)
NID_ENGINE

###### 684 (New OpenETCS Requirement Type)

###### 685: Zeile (New OpenETCS Requirement Type)

###### 686 (New OpenETCS Requirement Type)

###### 687 (New OpenETCS Requirement Type)
Packet 0 or 1

###### 688 (New OpenETCS Requirement Type)

###### 689: Zeile (New OpenETCS Requirement Type)

###### 690 (New OpenETCS Requirement Type)

###### 691 (New OpenETCS Requirement Type)
Optional packets

###### 692 (New OpenETCS Requirement Type)

#### 693: 8.6.5 Message 137: Request to Shorten MA is granted (New OpenETCS Requirement Type)

##### 694: Tabelle (New OpenETCS Requirement Type)

###### 695: Zeile (New OpenETCS Requirement Type)

###### 696 (New OpenETCS Requirement Type)
Field No.

###### 697 (New OpenETCS Requirement Type)
VARIABLE/ PACKET

###### 698 (New OpenETCS Requirement Type)
Remarks

###### 699: Zeile (New OpenETCS Requirement Type)

###### 700 (New OpenETCS Requirement Type)

###### 701 (New OpenETCS Requirement Type)
NID_MESSAGE

###### 702 (New OpenETCS Requirement Type)

###### 703: Zeile (New OpenETCS Requirement Type)

###### 704 (New OpenETCS Requirement Type)

###### 705 (New OpenETCS Requirement Type)
L_MESSAGE

###### 706 (New OpenETCS Requirement Type)

###### 707: Zeile (New OpenETCS Requirement Type)

###### 708 (New OpenETCS Requirement Type)

###### 709 (New OpenETCS Requirement Type)
T_TRAIN

###### 710 (New OpenETCS Requirement Type)

###### 711: Zeile (New OpenETCS Requirement Type)

###### 712 (New OpenETCS Requirement Type)

###### 713 (New OpenETCS Requirement Type)
NID_ENGINE

###### 714 (New OpenETCS Requirement Type)

###### 715: Zeile (New OpenETCS Requirement Type)

###### 716 (New OpenETCS Requirement Type)

###### 717 (New OpenETCS Requirement Type)
T_TRAIN

###### 718 (New OpenETCS Requirement Type)
Time stamp contained in the request.

###### 719: Zeile (New OpenETCS Requirement Type)

###### 720 (New OpenETCS Requirement Type)

###### 721 (New OpenETCS Requirement Type)
Packet 0 or 1

###### 722 (New OpenETCS Requirement Type)

#### 723: 8.6.6 Message 138: Request to Shorten MA is rejected (New OpenETCS Requirement Type)

##### 724: Tabelle (New OpenETCS Requirement Type)

###### 725: Zeile (New OpenETCS Requirement Type)

###### 726 (New OpenETCS Requirement Type)
Field No.

###### 727 (New OpenETCS Requirement Type)
VARIABLE/ PACKET

###### 728 (New OpenETCS Requirement Type)
Remarks

###### 729: Zeile (New OpenETCS Requirement Type)

###### 730 (New OpenETCS Requirement Type)

###### 731 (New OpenETCS Requirement Type)
NID_MESSAGE

###### 732 (New OpenETCS Requirement Type)

###### 733: Zeile (New OpenETCS Requirement Type)

###### 734 (New OpenETCS Requirement Type)

###### 735 (New OpenETCS Requirement Type)
L_MESSAGE

###### 736 (New OpenETCS Requirement Type)

###### 737: Zeile (New OpenETCS Requirement Type)

###### 738 (New OpenETCS Requirement Type)

###### 739 (New OpenETCS Requirement Type)
T_TRAIN

###### 740 (New OpenETCS Requirement Type)

###### 741: Zeile (New OpenETCS Requirement Type)

###### 742 (New OpenETCS Requirement Type)

###### 743 (New OpenETCS Requirement Type)
NID_ENGINE

###### 744 (New OpenETCS Requirement Type)

###### 745: Zeile (New OpenETCS Requirement Type)

###### 746 (New OpenETCS Requirement Type)

###### 747 (New OpenETCS Requirement Type)
T_TRAIN

###### 748 (New OpenETCS Requirement Type)
Time stamp contained in the request.

###### 749: Zeile (New OpenETCS Requirement Type)

###### 750 (New OpenETCS Requirement Type)

###### 751 (New OpenETCS Requirement Type)
Packet 0 or 1

###### 752 (New OpenETCS Requirement Type)

#### 753: 8.6.7 Message 146: Acknowledgement (New OpenETCS Requirement Type)

##### 754: Tabelle (New OpenETCS Requirement Type)

###### 755: Zeile (New OpenETCS Requirement Type)

###### 756 (New OpenETCS Requirement Type)
Field No.

###### 757 (New OpenETCS Requirement Type)
VARIABLE

###### 758 (New OpenETCS Requirement Type)
Remarks

###### 759: Zeile (New OpenETCS Requirement Type)

###### 760 (New OpenETCS Requirement Type)

###### 761 (New OpenETCS Requirement Type)
NID_MESSAGE

###### 762 (New OpenETCS Requirement Type)

###### 763: Zeile (New OpenETCS Requirement Type)

###### 764 (New OpenETCS Requirement Type)

###### 765 (New OpenETCS Requirement Type)
L_MESSAGE

###### 766 (New OpenETCS Requirement Type)

###### 767: Zeile (New OpenETCS Requirement Type)

###### 768 (New OpenETCS Requirement Type)

###### 769 (New OpenETCS Requirement Type)
T_TRAIN

###### 770 (New OpenETCS Requirement Type)

###### 771: Zeile (New OpenETCS Requirement Type)

###### 772 (New OpenETCS Requirement Type)

###### 773 (New OpenETCS Requirement Type)
NID_ENGINE

###### 774 (New OpenETCS Requirement Type)

###### 775: Zeile (New OpenETCS Requirement Type)

###### 776 (New OpenETCS Requirement Type)

###### 777 (New OpenETCS Requirement Type)
T_TRAIN

###### 778 (New OpenETCS Requirement Type)
Time stamp contained in the message that is acknowledged.

#### 779: 8.6.8 Message 147: Acknowledgement of Emergency Stop (New OpenETCS Requirement Type)

##### 780: Tabelle (New OpenETCS Requirement Type)

###### 781: Zeile (New OpenETCS Requirement Type)

###### 782 (New OpenETCS Requirement Type)
Field No.

###### 783 (New OpenETCS Requirement Type)
VARIABLE

###### 784 (New OpenETCS Requirement Type)
Remarks

###### 785: Zeile (New OpenETCS Requirement Type)

###### 786 (New OpenETCS Requirement Type)

###### 787 (New OpenETCS Requirement Type)
NID_MESSAGE

###### 788 (New OpenETCS Requirement Type)

###### 789: Zeile (New OpenETCS Requirement Type)

###### 790 (New OpenETCS Requirement Type)

###### 791 (New OpenETCS Requirement Type)
L_MESSAGE

###### 792 (New OpenETCS Requirement Type)

###### 793: Zeile (New OpenETCS Requirement Type)

###### 794 (New OpenETCS Requirement Type)

###### 795 (New OpenETCS Requirement Type)
T_TRAIN

###### 796 (New OpenETCS Requirement Type)

###### 797: Zeile (New OpenETCS Requirement Type)

###### 798 (New OpenETCS Requirement Type)

###### 799 (New OpenETCS Requirement Type)
NID_ENGINE

###### 800 (New OpenETCS Requirement Type)

###### 801: Zeile (New OpenETCS Requirement Type)

###### 802 (New OpenETCS Requirement Type)

###### 803 (New OpenETCS Requirement Type)
NID_EM

###### 804 (New OpenETCS Requirement Type)
Identification Number of the acknowledged Emergency Message.

###### 805: Zeile (New OpenETCS Requirement Type)

###### 806 (New OpenETCS Requirement Type)

###### 807 (New OpenETCS Requirement Type)
Q_EMERGENCYSTOP

###### 808 (New OpenETCS Requirement Type)

###### 809: Zeile (New OpenETCS Requirement Type)

###### 810 (New OpenETCS Requirement Type)

###### 811 (New OpenETCS Requirement Type)
Packet 0 or 1

###### 812 (New OpenETCS Requirement Type)

#### 813: 8.6.9 Message 149: Track Ahead Free Granted (New OpenETCS Requirement Type)

##### 814: Tabelle (New OpenETCS Requirement Type)

###### 815: Zeile (New OpenETCS Requirement Type)

###### 816 (New OpenETCS Requirement Type)
Field No.

###### 817 (New OpenETCS Requirement Type)
VARIABLE/ PACKET

###### 818 (New OpenETCS Requirement Type)
Remarks

###### 819: Zeile (New OpenETCS Requirement Type)

###### 820 (New OpenETCS Requirement Type)

###### 821 (New OpenETCS Requirement Type)
NID_MESSAGE

###### 822 (New OpenETCS Requirement Type)

###### 823: Zeile (New OpenETCS Requirement Type)

###### 824 (New OpenETCS Requirement Type)

###### 825 (New OpenETCS Requirement Type)
L_MESSAGE

###### 826 (New OpenETCS Requirement Type)

###### 827: Zeile (New OpenETCS Requirement Type)

###### 828 (New OpenETCS Requirement Type)

###### 829 (New OpenETCS Requirement Type)
T_TRAIN

###### 830 (New OpenETCS Requirement Type)

###### 831: Zeile (New OpenETCS Requirement Type)

###### 832 (New OpenETCS Requirement Type)

###### 833 (New OpenETCS Requirement Type)
NID_ENGINE

###### 834 (New OpenETCS Requirement Type)

###### 835: Zeile (New OpenETCS Requirement Type)

###### 836 (New OpenETCS Requirement Type)

###### 837 (New OpenETCS Requirement Type)
Packet 0 or 1

###### 838 (New OpenETCS Requirement Type)

#### 839: 8.6.10 Message 150: End of Mission (New OpenETCS Requirement Type)

##### 840: Tabelle (New OpenETCS Requirement Type)

###### 841: Zeile (New OpenETCS Requirement Type)

###### 842 (New OpenETCS Requirement Type)
Field No.

###### 843 (New OpenETCS Requirement Type)
VARIABLE/ PACKET

###### 844 (New OpenETCS Requirement Type)
Remarks

###### 845: Zeile (New OpenETCS Requirement Type)

###### 846 (New OpenETCS Requirement Type)

###### 847 (New OpenETCS Requirement Type)
NID_MESSAGE

###### 848 (New OpenETCS Requirement Type)

###### 849: Zeile (New OpenETCS Requirement Type)

###### 850 (New OpenETCS Requirement Type)

###### 851 (New OpenETCS Requirement Type)
L_MESSAGE

###### 852 (New OpenETCS Requirement Type)

###### 853: Zeile (New OpenETCS Requirement Type)

###### 854 (New OpenETCS Requirement Type)

###### 855 (New OpenETCS Requirement Type)
T_TRAIN

###### 856 (New OpenETCS Requirement Type)

###### 857: Zeile (New OpenETCS Requirement Type)

###### 858 (New OpenETCS Requirement Type)

###### 859 (New OpenETCS Requirement Type)
NID_ENGINE

###### 860 (New OpenETCS Requirement Type)

###### 861: Zeile (New OpenETCS Requirement Type)

###### 862 (New OpenETCS Requirement Type)

###### 863 (New OpenETCS Requirement Type)
Packet 0 or 1

###### 864 (New OpenETCS Requirement Type)

#### 865: 8.6.11 Message 153: Radio infill request (New OpenETCS Requirement Type)

##### 866: Tabelle (New OpenETCS Requirement Type)

###### 867: Zeile (New OpenETCS Requirement Type)

###### 868 (New OpenETCS Requirement Type)
Field No.

###### 869 (New OpenETCS Requirement Type)
VARIABLE

###### 870 (New OpenETCS Requirement Type)
Remarks

###### 871: Zeile (New OpenETCS Requirement Type)

###### 872 (New OpenETCS Requirement Type)

###### 873 (New OpenETCS Requirement Type)
NID_MESSAGE

###### 874 (New OpenETCS Requirement Type)

###### 875: Zeile (New OpenETCS Requirement Type)

###### 876 (New OpenETCS Requirement Type)

###### 877 (New OpenETCS Requirement Type)
L_MESSAGE

###### 878 (New OpenETCS Requirement Type)

###### 879: Zeile (New OpenETCS Requirement Type)

###### 880 (New OpenETCS Requirement Type)

###### 881 (New OpenETCS Requirement Type)
T_TRAIN

###### 882 (New OpenETCS Requirement Type)

###### 883: Zeile (New OpenETCS Requirement Type)

###### 884 (New OpenETCS Requirement Type)

###### 885 (New OpenETCS Requirement Type)
NID_ENGINE

###### 886 (New OpenETCS Requirement Type)

###### 887: Zeile (New OpenETCS Requirement Type)

###### 888 (New OpenETCS Requirement Type)

###### 889 (New OpenETCS Requirement Type)
NID_C

###### 890 (New OpenETCS Requirement Type)
identity of the country of the “target” main balise group

###### 891: Zeile (New OpenETCS Requirement Type)

###### 892 (New OpenETCS Requirement Type)

###### 893 (New OpenETCS Requirement Type)
NID_BG

###### 894 (New OpenETCS Requirement Type)
identity of the “target” main balise group

###### 895: Zeile (New OpenETCS Requirement Type)

###### 896 (New OpenETCS Requirement Type)

###### 897 (New OpenETCS Requirement Type)
Q_INFILL

###### 898 (New OpenETCS Requirement Type)
start; end of infill

###### 899: Zeile (New OpenETCS Requirement Type)

###### 900 (New OpenETCS Requirement Type)

###### 901 (New OpenETCS Requirement Type)
Packet 0 or 1

###### 902 (New OpenETCS Requirement Type)

#### 903: 8.6.12 Message 154: No compatible version supported (New OpenETCS Requirement Type)

##### 904: Tabelle (New OpenETCS Requirement Type)

###### 905: Zeile (New OpenETCS Requirement Type)

###### 906 (New OpenETCS Requirement Type)
Field No.

###### 907 (New OpenETCS Requirement Type)
VARIABLE/ PACKET

###### 908 (New OpenETCS Requirement Type)
Remarks

###### 909: Zeile (New OpenETCS Requirement Type)

###### 910 (New OpenETCS Requirement Type)

###### 911 (New OpenETCS Requirement Type)
NID_MESSAGE

###### 912 (New OpenETCS Requirement Type)

###### 913: Zeile (New OpenETCS Requirement Type)

###### 914 (New OpenETCS Requirement Type)

###### 915 (New OpenETCS Requirement Type)
L_MESSAGE

###### 916 (New OpenETCS Requirement Type)

###### 917: Zeile (New OpenETCS Requirement Type)

###### 918 (New OpenETCS Requirement Type)

###### 919 (New OpenETCS Requirement Type)
T_TRAIN

###### 920 (New OpenETCS Requirement Type)

###### 921: Zeile (New OpenETCS Requirement Type)

###### 922 (New OpenETCS Requirement Type)

###### 923 (New OpenETCS Requirement Type)
NID_ENGINE

###### 924 (New OpenETCS Requirement Type)

#### 925: 8.6.13 Message 155: Initiation of a communication session (New OpenETCS Requirement Type)

##### 926: Tabelle (New OpenETCS Requirement Type)

###### 927: Zeile (New OpenETCS Requirement Type)

###### 928 (New OpenETCS Requirement Type)
Field No.

###### 929 (New OpenETCS Requirement Type)
VARIABLE/ PACKET

###### 930 (New OpenETCS Requirement Type)
Remarks

###### 931: Zeile (New OpenETCS Requirement Type)

###### 932 (New OpenETCS Requirement Type)

###### 933 (New OpenETCS Requirement Type)
NID_MESSAGE

###### 934 (New OpenETCS Requirement Type)

###### 935: Zeile (New OpenETCS Requirement Type)

###### 936 (New OpenETCS Requirement Type)

###### 937 (New OpenETCS Requirement Type)
L_MESSAGE

###### 938 (New OpenETCS Requirement Type)

###### 939: Zeile (New OpenETCS Requirement Type)

###### 940 (New OpenETCS Requirement Type)

###### 941 (New OpenETCS Requirement Type)
T_TRAIN

###### 942 (New OpenETCS Requirement Type)

###### 943: Zeile (New OpenETCS Requirement Type)

###### 944 (New OpenETCS Requirement Type)

###### 945 (New OpenETCS Requirement Type)
NID_ENGINE

###### 946 (New OpenETCS Requirement Type)

#### 947: 8.6.14 Message 156: Termination of a communication session (New OpenETCS Requirement Type)

##### 948: Tabelle (New OpenETCS Requirement Type)

###### 949: Zeile (New OpenETCS Requirement Type)

###### 950 (New OpenETCS Requirement Type)
Field No.

###### 951 (New OpenETCS Requirement Type)
VARIABLE/ PACKET

###### 952 (New OpenETCS Requirement Type)
Remarks

###### 953: Zeile (New OpenETCS Requirement Type)

###### 954 (New OpenETCS Requirement Type)

###### 955 (New OpenETCS Requirement Type)
NID_MESSAGE

###### 956 (New OpenETCS Requirement Type)

###### 957: Zeile (New OpenETCS Requirement Type)

###### 958 (New OpenETCS Requirement Type)

###### 959 (New OpenETCS Requirement Type)
L_MESSAGE

###### 960 (New OpenETCS Requirement Type)

###### 961: Zeile (New OpenETCS Requirement Type)

###### 962 (New OpenETCS Requirement Type)

###### 963 (New OpenETCS Requirement Type)
T_TRAIN

###### 964 (New OpenETCS Requirement Type)

###### 965: Zeile (New OpenETCS Requirement Type)

###### 966 (New OpenETCS Requirement Type)

###### 967 (New OpenETCS Requirement Type)
NID_ENGINE

###### 968 (New OpenETCS Requirement Type)

#### 969: 8.6.15 Message 157: SoM Position Report (New OpenETCS Requirement Type)

##### 970: Tabelle (New OpenETCS Requirement Type)

###### 971: Zeile (New OpenETCS Requirement Type)

###### 972 (New OpenETCS Requirement Type)
Field No.

###### 973 (New OpenETCS Requirement Type)
VARIABLE/ PACKET

###### 974 (New OpenETCS Requirement Type)
Remarks

###### 975: Zeile (New OpenETCS Requirement Type)

###### 976 (New OpenETCS Requirement Type)

###### 977 (New OpenETCS Requirement Type)
NID_MESSAGE

###### 978 (New OpenETCS Requirement Type)

###### 979: Zeile (New OpenETCS Requirement Type)

###### 980 (New OpenETCS Requirement Type)

###### 981 (New OpenETCS Requirement Type)
L_MESSAGE

###### 982 (New OpenETCS Requirement Type)

###### 983: Zeile (New OpenETCS Requirement Type)

###### 984 (New OpenETCS Requirement Type)

###### 985 (New OpenETCS Requirement Type)
T_TRAIN

###### 986 (New OpenETCS Requirement Type)

###### 987: Zeile (New OpenETCS Requirement Type)

###### 988 (New OpenETCS Requirement Type)

###### 989 (New OpenETCS Requirement Type)
NID_ENGINE

###### 990 (New OpenETCS Requirement Type)

###### 991: Zeile (New OpenETCS Requirement Type)

###### 992 (New OpenETCS Requirement Type)

###### 993 (New OpenETCS Requirement Type)
Q_STATUS

###### 994 (New OpenETCS Requirement Type)

###### 995: Zeile (New OpenETCS Requirement Type)

###### 996 (New OpenETCS Requirement Type)

###### 997 (New OpenETCS Requirement Type)
Packet 0 or 1

###### 998 (New OpenETCS Requirement Type)

###### 999: Zeile (New OpenETCS Requirement Type)

###### 1000 (New OpenETCS Requirement Type)

###### 1001 (New OpenETCS Requirement Type)
Optional packets

###### 1002 (New OpenETCS Requirement Type)

#### 1003: 8.6.16 Message 158: Text Message Acknowledged by Driver (New OpenETCS Requirement Type)

##### 1004: Tabelle (New OpenETCS Requirement Type)

###### 1005: Zeile (New OpenETCS Requirement Type)

###### 1006 (New OpenETCS Requirement Type)
Field No.

###### 1007 (New OpenETCS Requirement Type)
VARIABLE/ PACKET

###### 1008 (New OpenETCS Requirement Type)
Remarks

###### 1009: Zeile (New OpenETCS Requirement Type)

###### 1010 (New OpenETCS Requirement Type)

###### 1011 (New OpenETCS Requirement Type)
NID_MESSAGE

###### 1012 (New OpenETCS Requirement Type)

###### 1013: Zeile (New OpenETCS Requirement Type)

###### 1014 (New OpenETCS Requirement Type)

###### 1015 (New OpenETCS Requirement Type)
L_MESSAGE

###### 1016 (New OpenETCS Requirement Type)

###### 1017: Zeile (New OpenETCS Requirement Type)

###### 1018 (New OpenETCS Requirement Type)

###### 1019 (New OpenETCS Requirement Type)
T_TRAIN

###### 1020 (New OpenETCS Requirement Type)

###### 1021: Zeile (New OpenETCS Requirement Type)

###### 1022 (New OpenETCS Requirement Type)

###### 1023 (New OpenETCS Requirement Type)
NID_ENGINE

###### 1024 (New OpenETCS Requirement Type)

###### 1025: Zeile (New OpenETCS Requirement Type)

###### 1026 (New OpenETCS Requirement Type)

###### 1027 (New OpenETCS Requirement Type)
NID_TEXTMESSAGE

###### 1028 (New OpenETCS Requirement Type)
Identity of the text message that the driver has acknowledged.

###### 1029: Zeile (New OpenETCS Requirement Type)

###### 1030 (New OpenETCS Requirement Type)

###### 1031 (New OpenETCS Requirement Type)
Packet 0 or 1

###### 1032 (New OpenETCS Requirement Type)

#### 1033: 8.6.17 Message 159: Session established (New OpenETCS Requirement Type)

##### 1034: Tabelle (New OpenETCS Requirement Type)

###### 1035: Zeile (New OpenETCS Requirement Type)

###### 1036 (New OpenETCS Requirement Type)
Field No.

###### 1037 (New OpenETCS Requirement Type)
VARIABLE/ PACKET

###### 1038 (New OpenETCS Requirement Type)
Remarks

###### 1039: Zeile (New OpenETCS Requirement Type)

###### 1040 (New OpenETCS Requirement Type)
1

###### 1041 (New OpenETCS Requirement Type)
NID_MESSAGE

###### 1042 (New OpenETCS Requirement Type)

###### 1043: Zeile (New OpenETCS Requirement Type)

###### 1044 (New OpenETCS Requirement Type)
2

###### 1045 (New OpenETCS Requirement Type)
L_MESSAGE

###### 1046 (New OpenETCS Requirement Type)

###### 1047: Zeile (New OpenETCS Requirement Type)

###### 1048 (New OpenETCS Requirement Type)
3

###### 1049 (New OpenETCS Requirement Type)
T_TRAIN

###### 1050 (New OpenETCS Requirement Type)

###### 1051: Zeile (New OpenETCS Requirement Type)

###### 1052 (New OpenETCS Requirement Type)
4

###### 1053 (New OpenETCS Requirement Type)
NID_ENGINE

###### 1054 (New OpenETCS Requirement Type)

###### 1055: Zeile (New OpenETCS Requirement Type)

###### 1056 (New OpenETCS Requirement Type)
5

###### 1057 (New OpenETCS Requirement Type)
Optional Packet

###### 1058 (New OpenETCS Requirement Type)

### 1059: 8.7 Definition of Radio Messages from Track to Train (New OpenETCS Requirement Type)

#### 1060: 8.7.1 Message 2: SR Authorisation (New OpenETCS Requirement Type)

##### 1061: Tabelle (New OpenETCS Requirement Type)

###### 1062: Zeile (New OpenETCS Requirement Type)

###### 1063 (New OpenETCS Requirement Type)
Field No.

###### 1064 (New OpenETCS Requirement Type)
VARIABLE

###### 1065 (New OpenETCS Requirement Type)
Remarks

###### 1066: Zeile (New OpenETCS Requirement Type)

###### 1067 (New OpenETCS Requirement Type)

###### 1068 (New OpenETCS Requirement Type)
NID_MESSAGE

###### 1069 (New OpenETCS Requirement Type)

###### 1070: Zeile (New OpenETCS Requirement Type)

###### 1071 (New OpenETCS Requirement Type)

###### 1072 (New OpenETCS Requirement Type)
L_MESSAGE

###### 1073 (New OpenETCS Requirement Type)

###### 1074: Zeile (New OpenETCS Requirement Type)

###### 1075 (New OpenETCS Requirement Type)

###### 1076 (New OpenETCS Requirement Type)
T_TRAIN

###### 1077 (New OpenETCS Requirement Type)

###### 1078: Zeile (New OpenETCS Requirement Type)

###### 1079 (New OpenETCS Requirement Type)

###### 1080 (New OpenETCS Requirement Type)
M_ACK

###### 1081 (New OpenETCS Requirement Type)

###### 1082: Zeile (New OpenETCS Requirement Type)

###### 1083 (New OpenETCS Requirement Type)

###### 1084 (New OpenETCS Requirement Type)
NID_LRBG

###### 1085 (New OpenETCS Requirement Type)

###### 1086: Zeile (New OpenETCS Requirement Type)

###### 1087 (New OpenETCS Requirement Type)

###### 1088 (New OpenETCS Requirement Type)
Q_SCALE

###### 1089 (New OpenETCS Requirement Type)

###### 1090: Zeile (New OpenETCS Requirement Type)

###### 1091 (New OpenETCS Requirement Type)

###### 1092 (New OpenETCS Requirement Type)
D_SR

###### 1093 (New OpenETCS Requirement Type)

###### 1094: Zeile (New OpenETCS Requirement Type)

###### 1095 (New OpenETCS Requirement Type)

###### 1096 (New OpenETCS Requirement Type)
Optional packets

###### 1097 (New OpenETCS Requirement Type)

#### 1098: 8.7.2 Message 3: Movement Authority (New OpenETCS Requirement Type)

##### 1099: Tabelle (New OpenETCS Requirement Type)

###### 1100: Zeile (New OpenETCS Requirement Type)

###### 1101 (New OpenETCS Requirement Type)
Field No.

###### 1102 (New OpenETCS Requirement Type)
VARIABLE

###### 1103 (New OpenETCS Requirement Type)
Remarks

###### 1104: Zeile (New OpenETCS Requirement Type)

###### 1105 (New OpenETCS Requirement Type)

###### 1106 (New OpenETCS Requirement Type)
NID_MESSAGE

###### 1107 (New OpenETCS Requirement Type)

###### 1108: Zeile (New OpenETCS Requirement Type)

###### 1109 (New OpenETCS Requirement Type)

###### 1110 (New OpenETCS Requirement Type)
L_MESSAGE

###### 1111 (New OpenETCS Requirement Type)

###### 1112: Zeile (New OpenETCS Requirement Type)

###### 1113 (New OpenETCS Requirement Type)

###### 1114 (New OpenETCS Requirement Type)
T_TRAIN

###### 1115 (New OpenETCS Requirement Type)

###### 1116: Zeile (New OpenETCS Requirement Type)

###### 1117 (New OpenETCS Requirement Type)

###### 1118 (New OpenETCS Requirement Type)
M_ACK

###### 1119 (New OpenETCS Requirement Type)

###### 1120: Zeile (New OpenETCS Requirement Type)

###### 1121 (New OpenETCS Requirement Type)

###### 1122 (New OpenETCS Requirement Type)
NID_LRBG

###### 1123 (New OpenETCS Requirement Type)

###### 1124: Zeile (New OpenETCS Requirement Type)

###### 1125 (New OpenETCS Requirement Type)

###### 1126 (New OpenETCS Requirement Type)
Level 2/3 Movement Authority

###### 1127 (New OpenETCS Requirement Type)
Packet 15

###### 1128: Zeile (New OpenETCS Requirement Type)

###### 1129 (New OpenETCS Requirement Type)

###### 1130 (New OpenETCS Requirement Type)
Optional packets

###### 1131 (New OpenETCS Requirement Type)

#### 1132: 8.7.3 Message 6: Recognition of exit from TRIP mode (New OpenETCS Requirement Type)

##### 1133: Tabelle (New OpenETCS Requirement Type)

###### 1134: Zeile (New OpenETCS Requirement Type)

###### 1135 (New OpenETCS Requirement Type)
Field No.

###### 1136 (New OpenETCS Requirement Type)
VARIABLE

###### 1137 (New OpenETCS Requirement Type)
Remarks

###### 1138: Zeile (New OpenETCS Requirement Type)

###### 1139 (New OpenETCS Requirement Type)

###### 1140 (New OpenETCS Requirement Type)
NID_MESSAGE

###### 1141 (New OpenETCS Requirement Type)

###### 1142: Zeile (New OpenETCS Requirement Type)

###### 1143 (New OpenETCS Requirement Type)

###### 1144 (New OpenETCS Requirement Type)
L_MESSAGE

###### 1145 (New OpenETCS Requirement Type)

###### 1146: Zeile (New OpenETCS Requirement Type)

###### 1147 (New OpenETCS Requirement Type)

###### 1148 (New OpenETCS Requirement Type)
T_TRAIN

###### 1149 (New OpenETCS Requirement Type)

###### 1150: Zeile (New OpenETCS Requirement Type)

###### 1151 (New OpenETCS Requirement Type)

###### 1152 (New OpenETCS Requirement Type)
M_ACK

###### 1153 (New OpenETCS Requirement Type)

###### 1154: Zeile (New OpenETCS Requirement Type)

###### 1155 (New OpenETCS Requirement Type)

###### 1156 (New OpenETCS Requirement Type)
NID_LRBG

###### 1157 (New OpenETCS Requirement Type)

#### 1158: 8.7.4 Message 8: Acknowledgement of Train Data (New OpenETCS Requirement Type)

##### 1159: Tabelle (New OpenETCS Requirement Type)

###### 1160: Zeile (New OpenETCS Requirement Type)

###### 1161 (New OpenETCS Requirement Type)
Field No.

###### 1162 (New OpenETCS Requirement Type)
VARIABLE

###### 1163 (New OpenETCS Requirement Type)
Remarks

###### 1164: Zeile (New OpenETCS Requirement Type)

###### 1165 (New OpenETCS Requirement Type)

###### 1166 (New OpenETCS Requirement Type)
NID_MESSAGE

###### 1167 (New OpenETCS Requirement Type)

###### 1168: Zeile (New OpenETCS Requirement Type)

###### 1169 (New OpenETCS Requirement Type)

###### 1170 (New OpenETCS Requirement Type)
L_MESSAGE

###### 1171 (New OpenETCS Requirement Type)

###### 1172: Zeile (New OpenETCS Requirement Type)

###### 1173 (New OpenETCS Requirement Type)

###### 1174 (New OpenETCS Requirement Type)
T_TRAIN

###### 1175 (New OpenETCS Requirement Type)

###### 1176: Zeile (New OpenETCS Requirement Type)

###### 1177 (New OpenETCS Requirement Type)

###### 1178 (New OpenETCS Requirement Type)
M_ACK

###### 1179 (New OpenETCS Requirement Type)

###### 1180: Zeile (New OpenETCS Requirement Type)

###### 1181 (New OpenETCS Requirement Type)

###### 1182 (New OpenETCS Requirement Type)
NID_LRBG

###### 1183 (New OpenETCS Requirement Type)

###### 1184: Zeile (New OpenETCS Requirement Type)

###### 1185 (New OpenETCS Requirement Type)

###### 1186 (New OpenETCS Requirement Type)
T_TRAIN

###### 1187 (New OpenETCS Requirement Type)
Reference to received train data message

#### 1188: 8.7.5 Message 9: Request to Shorten MA (New OpenETCS Requirement Type)

##### 1189: Tabelle (New OpenETCS Requirement Type)

###### 1190: Zeile (New OpenETCS Requirement Type)

###### 1191 (New OpenETCS Requirement Type)
Field No.

###### 1192 (New OpenETCS Requirement Type)
VARIABLE

###### 1193 (New OpenETCS Requirement Type)
Remarks

###### 1194: Zeile (New OpenETCS Requirement Type)

###### 1195 (New OpenETCS Requirement Type)

###### 1196 (New OpenETCS Requirement Type)
NID_MESSAGE

###### 1197 (New OpenETCS Requirement Type)

###### 1198: Zeile (New OpenETCS Requirement Type)

###### 1199 (New OpenETCS Requirement Type)

###### 1200 (New OpenETCS Requirement Type)
L_MESSAGE

###### 1201 (New OpenETCS Requirement Type)

###### 1202: Zeile (New OpenETCS Requirement Type)

###### 1203 (New OpenETCS Requirement Type)

###### 1204 (New OpenETCS Requirement Type)
T_TRAIN

###### 1205 (New OpenETCS Requirement Type)

###### 1206: Zeile (New OpenETCS Requirement Type)

###### 1207 (New OpenETCS Requirement Type)

###### 1208 (New OpenETCS Requirement Type)
M_ACK

###### 1209 (New OpenETCS Requirement Type)

###### 1210: Zeile (New OpenETCS Requirement Type)

###### 1211 (New OpenETCS Requirement Type)

###### 1212 (New OpenETCS Requirement Type)
NID_LRBG

###### 1213 (New OpenETCS Requirement Type)

###### 1214: Zeile (New OpenETCS Requirement Type)

###### 1215 (New OpenETCS Requirement Type)

###### 1216 (New OpenETCS Requirement Type)
Level 2/3 Movement Authority

###### 1217 (New OpenETCS Requirement Type)
Packet 15

###### 1218: Zeile (New OpenETCS Requirement Type)

###### 1219 (New OpenETCS Requirement Type)

###### 1220 (New OpenETCS Requirement Type)
Optional packet

###### 1221 (New OpenETCS Requirement Type)
Packet 80

#### 1222: 8.7.6 Message 15: Conditional Emergency Stop (New OpenETCS Requirement Type)

##### 1223: Tabelle (New OpenETCS Requirement Type)

###### 1224: Zeile (New OpenETCS Requirement Type)

###### 1225 (New OpenETCS Requirement Type)
Field No.

###### 1226 (New OpenETCS Requirement Type)
VARIABLE

###### 1227 (New OpenETCS Requirement Type)
Remarks

###### 1228: Zeile (New OpenETCS Requirement Type)

###### 1229 (New OpenETCS Requirement Type)

###### 1230 (New OpenETCS Requirement Type)
NID_MESSAGE

###### 1231 (New OpenETCS Requirement Type)

###### 1232: Zeile (New OpenETCS Requirement Type)

###### 1233 (New OpenETCS Requirement Type)

###### 1234 (New OpenETCS Requirement Type)
L_MESSAGE

###### 1235 (New OpenETCS Requirement Type)

###### 1236: Zeile (New OpenETCS Requirement Type)

###### 1237 (New OpenETCS Requirement Type)

###### 1238 (New OpenETCS Requirement Type)
T_TRAIN

###### 1239 (New OpenETCS Requirement Type)

###### 1240: Zeile (New OpenETCS Requirement Type)

###### 1241 (New OpenETCS Requirement Type)

###### 1242 (New OpenETCS Requirement Type)
M_ACK

###### 1243 (New OpenETCS Requirement Type)

###### 1244: Zeile (New OpenETCS Requirement Type)

###### 1245 (New OpenETCS Requirement Type)

###### 1246 (New OpenETCS Requirement Type)
NID_LRBG

###### 1247 (New OpenETCS Requirement Type)

###### 1248: Zeile (New OpenETCS Requirement Type)

###### 1249 (New OpenETCS Requirement Type)

###### 1250 (New OpenETCS Requirement Type)
NID_EM

###### 1251 (New OpenETCS Requirement Type)
Identification Number of the Emergency Stop Message.

###### 1252: Zeile (New OpenETCS Requirement Type)

###### 1253 (New OpenETCS Requirement Type)

###### 1254 (New OpenETCS Requirement Type)
Q_SCALE

###### 1255 (New OpenETCS Requirement Type)

###### 1256: Zeile (New OpenETCS Requirement Type)

###### 1257 (New OpenETCS Requirement Type)

###### 1258 (New OpenETCS Requirement Type)
D_REF

###### 1259 (New OpenETCS Requirement Type)

###### 1260: Zeile (New OpenETCS Requirement Type)

###### 1261 (New OpenETCS Requirement Type)

###### 1262 (New OpenETCS Requirement Type)
Q_DIR

###### 1263 (New OpenETCS Requirement Type)

###### 1264: Zeile (New OpenETCS Requirement Type)

###### 1265 (New OpenETCS Requirement Type)

###### 1266 (New OpenETCS Requirement Type)
D_EMERGENCYSTOP

###### 1267 (New OpenETCS Requirement Type)
Distance between LRBG and the position reference to the emergency stop.

#### 1268: 8.7.7 Message 16: Unconditional Emergency Stop (New OpenETCS Requirement Type)

##### 1269: Tabelle (New OpenETCS Requirement Type)

###### 1270: Zeile (New OpenETCS Requirement Type)

###### 1271 (New OpenETCS Requirement Type)
Field No.

###### 1272 (New OpenETCS Requirement Type)
VARIABLE

###### 1273 (New OpenETCS Requirement Type)
Remarks

###### 1274: Zeile (New OpenETCS Requirement Type)

###### 1275 (New OpenETCS Requirement Type)

###### 1276 (New OpenETCS Requirement Type)
NID_MESSAGE

###### 1277 (New OpenETCS Requirement Type)

###### 1278: Zeile (New OpenETCS Requirement Type)

###### 1279 (New OpenETCS Requirement Type)

###### 1280 (New OpenETCS Requirement Type)
L_MESSAGE

###### 1281 (New OpenETCS Requirement Type)

###### 1282: Zeile (New OpenETCS Requirement Type)

###### 1283 (New OpenETCS Requirement Type)

###### 1284 (New OpenETCS Requirement Type)
T_TRAIN

###### 1285 (New OpenETCS Requirement Type)

###### 1286: Zeile (New OpenETCS Requirement Type)

###### 1287 (New OpenETCS Requirement Type)

###### 1288 (New OpenETCS Requirement Type)
M_ACK

###### 1289 (New OpenETCS Requirement Type)

###### 1290: Zeile (New OpenETCS Requirement Type)

###### 1291 (New OpenETCS Requirement Type)

###### 1292 (New OpenETCS Requirement Type)
NID_LRBG

###### 1293 (New OpenETCS Requirement Type)

###### 1294: Zeile (New OpenETCS Requirement Type)

###### 1295 (New OpenETCS Requirement Type)

###### 1296 (New OpenETCS Requirement Type)
NID_EM

###### 1297 (New OpenETCS Requirement Type)
Identification Number of the Emergency Stop Message.

#### 1298: 8.7.8 Message 18: Revocation of Emergency Stop (New OpenETCS Requirement Type)

##### 1299: Tabelle (New OpenETCS Requirement Type)

###### 1300: Zeile (New OpenETCS Requirement Type)

###### 1301 (New OpenETCS Requirement Type)
Field No.

###### 1302 (New OpenETCS Requirement Type)
VARIABLE

###### 1303 (New OpenETCS Requirement Type)
Remarks

###### 1304: Zeile (New OpenETCS Requirement Type)

###### 1305 (New OpenETCS Requirement Type)

###### 1306 (New OpenETCS Requirement Type)
NID_MESSAGE

###### 1307 (New OpenETCS Requirement Type)

###### 1308: Zeile (New OpenETCS Requirement Type)

###### 1309 (New OpenETCS Requirement Type)

###### 1310 (New OpenETCS Requirement Type)
L_MESSAGE

###### 1311 (New OpenETCS Requirement Type)

###### 1312: Zeile (New OpenETCS Requirement Type)

###### 1313 (New OpenETCS Requirement Type)

###### 1314 (New OpenETCS Requirement Type)
T_TRAIN

###### 1315 (New OpenETCS Requirement Type)

###### 1316: Zeile (New OpenETCS Requirement Type)

###### 1317 (New OpenETCS Requirement Type)

###### 1318 (New OpenETCS Requirement Type)
M_ACK

###### 1319 (New OpenETCS Requirement Type)

###### 1320: Zeile (New OpenETCS Requirement Type)

###### 1321 (New OpenETCS Requirement Type)

###### 1322 (New OpenETCS Requirement Type)
NID_LRBG

###### 1323 (New OpenETCS Requirement Type)

###### 1324: Zeile (New OpenETCS Requirement Type)

###### 1325 (New OpenETCS Requirement Type)

###### 1326 (New OpenETCS Requirement Type)
NID_EM

###### 1327 (New OpenETCS Requirement Type)
Identification Number of the Emergency Stop Message.

#### 1328: 8.7.9 Message 24: General message (New OpenETCS Requirement Type)

##### 1329: Tabelle (New OpenETCS Requirement Type)

###### 1330: Zeile (New OpenETCS Requirement Type)

###### 1331 (New OpenETCS Requirement Type)
Field No.

###### 1332 (New OpenETCS Requirement Type)
VARIABLE

###### 1333 (New OpenETCS Requirement Type)
Remarks

###### 1334: Zeile (New OpenETCS Requirement Type)

###### 1335 (New OpenETCS Requirement Type)

###### 1336 (New OpenETCS Requirement Type)
NID_MESSAGE

###### 1337 (New OpenETCS Requirement Type)

###### 1338: Zeile (New OpenETCS Requirement Type)

###### 1339 (New OpenETCS Requirement Type)

###### 1340 (New OpenETCS Requirement Type)
L_MESSAGE

###### 1341 (New OpenETCS Requirement Type)

###### 1342: Zeile (New OpenETCS Requirement Type)

###### 1343 (New OpenETCS Requirement Type)

###### 1344 (New OpenETCS Requirement Type)
T_TRAIN

###### 1345 (New OpenETCS Requirement Type)

###### 1346: Zeile (New OpenETCS Requirement Type)

###### 1347 (New OpenETCS Requirement Type)

###### 1348 (New OpenETCS Requirement Type)
M_ACK

###### 1349 (New OpenETCS Requirement Type)

###### 1350: Zeile (New OpenETCS Requirement Type)

###### 1351 (New OpenETCS Requirement Type)

###### 1352 (New OpenETCS Requirement Type)
NID_LRBG

###### 1353 (New OpenETCS Requirement Type)

###### 1354: Zeile (New OpenETCS Requirement Type)

###### 1355 (New OpenETCS Requirement Type)

###### 1356 (New OpenETCS Requirement Type)
Optional packets

###### 1357 (New OpenETCS Requirement Type)

#### 1358: 8.7.10 Message 27: SH Refused (New OpenETCS Requirement Type)

##### 1359: Tabelle (New OpenETCS Requirement Type)

###### 1360: Zeile (New OpenETCS Requirement Type)

###### 1361 (New OpenETCS Requirement Type)
Field No.

###### 1362 (New OpenETCS Requirement Type)
VARIABLE

###### 1363 (New OpenETCS Requirement Type)
Remarks

###### 1364: Zeile (New OpenETCS Requirement Type)

###### 1365 (New OpenETCS Requirement Type)

###### 1366 (New OpenETCS Requirement Type)
NID_MESSAGE

###### 1367 (New OpenETCS Requirement Type)

###### 1368: Zeile (New OpenETCS Requirement Type)

###### 1369 (New OpenETCS Requirement Type)

###### 1370 (New OpenETCS Requirement Type)
L_MESSAGE

###### 1371 (New OpenETCS Requirement Type)

###### 1372: Zeile (New OpenETCS Requirement Type)

###### 1373 (New OpenETCS Requirement Type)

###### 1374 (New OpenETCS Requirement Type)
T_TRAIN

###### 1375 (New OpenETCS Requirement Type)

###### 1376: Zeile (New OpenETCS Requirement Type)

###### 1377 (New OpenETCS Requirement Type)

###### 1378 (New OpenETCS Requirement Type)
M_ACK

###### 1379 (New OpenETCS Requirement Type)

###### 1380: Zeile (New OpenETCS Requirement Type)

###### 1381 (New OpenETCS Requirement Type)

###### 1382 (New OpenETCS Requirement Type)
NID_LRBG

###### 1383 (New OpenETCS Requirement Type)

###### 1384: Zeile (New OpenETCS Requirement Type)

###### 1385 (New OpenETCS Requirement Type)

###### 1386 (New OpenETCS Requirement Type)
T_TRAIN

###### 1387 (New OpenETCS Requirement Type)
Time stamp of the shunting request.

#### 1388: 8.7.11 Message 28: SH Authorised (New OpenETCS Requirement Type)

##### 1389: Tabelle (New OpenETCS Requirement Type)

###### 1390: Zeile (New OpenETCS Requirement Type)

###### 1391 (New OpenETCS Requirement Type)
Field No.

###### 1392 (New OpenETCS Requirement Type)
VARIABLE

###### 1393 (New OpenETCS Requirement Type)
Remarks

###### 1394: Zeile (New OpenETCS Requirement Type)

###### 1395 (New OpenETCS Requirement Type)

###### 1396 (New OpenETCS Requirement Type)
NID_MESSAGE

###### 1397 (New OpenETCS Requirement Type)

###### 1398: Zeile (New OpenETCS Requirement Type)

###### 1399 (New OpenETCS Requirement Type)

###### 1400 (New OpenETCS Requirement Type)
L_MESSAGE

###### 1401 (New OpenETCS Requirement Type)

###### 1402: Zeile (New OpenETCS Requirement Type)

###### 1403 (New OpenETCS Requirement Type)

###### 1404 (New OpenETCS Requirement Type)
T_TRAIN

###### 1405 (New OpenETCS Requirement Type)

###### 1406: Zeile (New OpenETCS Requirement Type)

###### 1407 (New OpenETCS Requirement Type)

###### 1408 (New OpenETCS Requirement Type)
M_ACK

###### 1409 (New OpenETCS Requirement Type)

###### 1410: Zeile (New OpenETCS Requirement Type)

###### 1411 (New OpenETCS Requirement Type)

###### 1412 (New OpenETCS Requirement Type)
NID_LRBG

###### 1413 (New OpenETCS Requirement Type)

###### 1414: Zeile (New OpenETCS Requirement Type)

###### 1415 (New OpenETCS Requirement Type)

###### 1416 (New OpenETCS Requirement Type)
T_TRAIN

###### 1417 (New OpenETCS Requirement Type)
Time stamp of the shunting request.

###### 1418: Zeile (New OpenETCS Requirement Type)

###### 1419 (New OpenETCS Requirement Type)

###### 1420 (New OpenETCS Requirement Type)
Optional packets

###### 1421 (New OpenETCS Requirement Type)

#### 1422: 8.7.12 Message 32: RBC/RIU System Version (New OpenETCS Requirement Type)

##### 1423: Tabelle (New OpenETCS Requirement Type)

###### 1424: Zeile (New OpenETCS Requirement Type)

###### 1425 (New OpenETCS Requirement Type)
Field No.

###### 1426 (New OpenETCS Requirement Type)
VARIABLE

###### 1427 (New OpenETCS Requirement Type)
Remarks

###### 1428: Zeile (New OpenETCS Requirement Type)

###### 1429 (New OpenETCS Requirement Type)

###### 1430 (New OpenETCS Requirement Type)
NID_MESSAGE

###### 1431 (New OpenETCS Requirement Type)

###### 1432: Zeile (New OpenETCS Requirement Type)

###### 1433 (New OpenETCS Requirement Type)

###### 1434 (New OpenETCS Requirement Type)
L_MESSAGE

###### 1435 (New OpenETCS Requirement Type)

###### 1436: Zeile (New OpenETCS Requirement Type)

###### 1437 (New OpenETCS Requirement Type)

###### 1438 (New OpenETCS Requirement Type)
T_TRAIN

###### 1439 (New OpenETCS Requirement Type)

###### 1440: Zeile (New OpenETCS Requirement Type)

###### 1441 (New OpenETCS Requirement Type)

###### 1442 (New OpenETCS Requirement Type)
M_ACK

###### 1443 (New OpenETCS Requirement Type)

###### 1444: Zeile (New OpenETCS Requirement Type)

###### 1445 (New OpenETCS Requirement Type)

###### 1446 (New OpenETCS Requirement Type)
NID_LRBG

###### 1447 (New OpenETCS Requirement Type)

###### 1448: Zeile (New OpenETCS Requirement Type)

###### 1449 (New OpenETCS Requirement Type)

###### 1450 (New OpenETCS Requirement Type)
M_VERSION

###### 1451 (New OpenETCS Requirement Type)
Version of the ERTMS/ETCS system.

#### 1452: 8.7.13 Message 33: MA with Shifted Location Reference (New OpenETCS Requirement Type)

##### 1453: Tabelle (New OpenETCS Requirement Type)

###### 1454: Zeile (New OpenETCS Requirement Type)

###### 1455 (New OpenETCS Requirement Type)
Field No.

###### 1456 (New OpenETCS Requirement Type)
VARIABLE

###### 1457 (New OpenETCS Requirement Type)
Remarks

###### 1458: Zeile (New OpenETCS Requirement Type)

###### 1459 (New OpenETCS Requirement Type)

###### 1460 (New OpenETCS Requirement Type)
NID_MESSAGE

###### 1461 (New OpenETCS Requirement Type)

###### 1462: Zeile (New OpenETCS Requirement Type)

###### 1463 (New OpenETCS Requirement Type)

###### 1464 (New OpenETCS Requirement Type)
L_MESSAGE

###### 1465 (New OpenETCS Requirement Type)

###### 1466: Zeile (New OpenETCS Requirement Type)

###### 1467 (New OpenETCS Requirement Type)

###### 1468 (New OpenETCS Requirement Type)
T_TRAIN

###### 1469 (New OpenETCS Requirement Type)

###### 1470: Zeile (New OpenETCS Requirement Type)

###### 1471 (New OpenETCS Requirement Type)

###### 1472 (New OpenETCS Requirement Type)
M_ACK

###### 1473 (New OpenETCS Requirement Type)

###### 1474: Zeile (New OpenETCS Requirement Type)

###### 1475 (New OpenETCS Requirement Type)

###### 1476 (New OpenETCS Requirement Type)
NID_LRBG

###### 1477 (New OpenETCS Requirement Type)

###### 1478: Zeile (New OpenETCS Requirement Type)

###### 1479 (New OpenETCS Requirement Type)

###### 1480 (New OpenETCS Requirement Type)
Q_SCALE

###### 1481 (New OpenETCS Requirement Type)

###### 1482: Zeile (New OpenETCS Requirement Type)

###### 1483 (New OpenETCS Requirement Type)

###### 1484 (New OpenETCS Requirement Type)
D_REF

###### 1485 (New OpenETCS Requirement Type)
Reference Distance

###### 1486: Zeile (New OpenETCS Requirement Type)

###### 1487 (New OpenETCS Requirement Type)

###### 1488 (New OpenETCS Requirement Type)
Level 2/3 Movement Authority

###### 1489 (New OpenETCS Requirement Type)
Packet 15

###### 1490: Zeile (New OpenETCS Requirement Type)

###### 1491 (New OpenETCS Requirement Type)

###### 1492 (New OpenETCS Requirement Type)
Optional packets

###### 1493 (New OpenETCS Requirement Type)

#### 1494: 8.7.14 Message 34: Track Ahead Free Request (New OpenETCS Requirement Type)

##### 1495: Tabelle (New OpenETCS Requirement Type)

###### 1496: Zeile (New OpenETCS Requirement Type)

###### 1497 (New OpenETCS Requirement Type)
Field No.

###### 1498 (New OpenETCS Requirement Type)
VARIABLE

###### 1499 (New OpenETCS Requirement Type)
Remarks

###### 1500: Zeile (New OpenETCS Requirement Type)

###### 1501 (New OpenETCS Requirement Type)

###### 1502 (New OpenETCS Requirement Type)
NID_MESSAGE

###### 1503 (New OpenETCS Requirement Type)

###### 1504: Zeile (New OpenETCS Requirement Type)

###### 1505 (New OpenETCS Requirement Type)

###### 1506 (New OpenETCS Requirement Type)
L_MESSAGE

###### 1507 (New OpenETCS Requirement Type)

###### 1508: Zeile (New OpenETCS Requirement Type)

###### 1509 (New OpenETCS Requirement Type)

###### 1510 (New OpenETCS Requirement Type)
T_TRAIN

###### 1511 (New OpenETCS Requirement Type)

###### 1512: Zeile (New OpenETCS Requirement Type)

###### 1513 (New OpenETCS Requirement Type)

###### 1514 (New OpenETCS Requirement Type)
M_ACK

###### 1515 (New OpenETCS Requirement Type)

###### 1516: Zeile (New OpenETCS Requirement Type)

###### 1517 (New OpenETCS Requirement Type)

###### 1518 (New OpenETCS Requirement Type)
NID_LRBG

###### 1519 (New OpenETCS Requirement Type)

###### 1520: Zeile (New OpenETCS Requirement Type)

###### 1521 (New OpenETCS Requirement Type)

###### 1522 (New OpenETCS Requirement Type)
Q_SCALE

###### 1523 (New OpenETCS Requirement Type)

###### 1524: Zeile (New OpenETCS Requirement Type)

###### 1525 (New OpenETCS Requirement Type)

###### 1526 (New OpenETCS Requirement Type)
D_REF

###### 1527 (New OpenETCS Requirement Type)

###### 1528: Zeile (New OpenETCS Requirement Type)

###### 1529 (New OpenETCS Requirement Type)

###### 1530 (New OpenETCS Requirement Type)
Q_DIR

###### 1531 (New OpenETCS Requirement Type)

###### 1532: Zeile (New OpenETCS Requirement Type)

###### 1533 (New OpenETCS Requirement Type)

###### 1534 (New OpenETCS Requirement Type)
D_TAFDISPLAY

###### 1535 (New OpenETCS Requirement Type)

###### 1536: Zeile (New OpenETCS Requirement Type)

###### 1537 (New OpenETCS Requirement Type)

###### 1538 (New OpenETCS Requirement Type)
L_TAFDISPLAY

###### 1539 (New OpenETCS Requirement Type)

#### 1540: 8.7.15 Message 37: Infill MA (New OpenETCS Requirement Type)

##### 1541: Tabelle (New OpenETCS Requirement Type)

###### 1542: Zeile (New OpenETCS Requirement Type)

###### 1543 (New OpenETCS Requirement Type)
Field No.

###### 1544 (New OpenETCS Requirement Type)
VARIABLE

###### 1545 (New OpenETCS Requirement Type)
Remarks

###### 1546: Zeile (New OpenETCS Requirement Type)

###### 1547 (New OpenETCS Requirement Type)

###### 1548 (New OpenETCS Requirement Type)
NID_MESSAGE

###### 1549 (New OpenETCS Requirement Type)

###### 1550: Zeile (New OpenETCS Requirement Type)

###### 1551 (New OpenETCS Requirement Type)

###### 1552 (New OpenETCS Requirement Type)
L_MESSAGE

###### 1553 (New OpenETCS Requirement Type)

###### 1554: Zeile (New OpenETCS Requirement Type)

###### 1555 (New OpenETCS Requirement Type)

###### 1556 (New OpenETCS Requirement Type)
T_TRAIN

###### 1557 (New OpenETCS Requirement Type)

###### 1558: Zeile (New OpenETCS Requirement Type)

###### 1559 (New OpenETCS Requirement Type)

###### 1560 (New OpenETCS Requirement Type)
M_ACK

###### 1561 (New OpenETCS Requirement Type)

###### 1562: Zeile (New OpenETCS Requirement Type)

###### 1563 (New OpenETCS Requirement Type)

###### 1564 (New OpenETCS Requirement Type)
NID_LRBG

###### 1565 (New OpenETCS Requirement Type)

###### 1566: Zeile (New OpenETCS Requirement Type)

###### 1567 (New OpenETCS Requirement Type)

###### 1568 (New OpenETCS Requirement Type)
Infill Location Reference

###### 1569 (New OpenETCS Requirement Type)
Packet 136

###### 1570: Zeile (New OpenETCS Requirement Type)

###### 1571 (New OpenETCS Requirement Type)

###### 1572 (New OpenETCS Requirement Type)
Level 1 Movement Authority

###### 1573 (New OpenETCS Requirement Type)
Packet 12

###### 1574: Zeile (New OpenETCS Requirement Type)

###### 1575 (New OpenETCS Requirement Type)

###### 1576 (New OpenETCS Requirement Type)
Optional packets

###### 1577 (New OpenETCS Requirement Type)

#### 1578: 8.7.16 Message 38: Initiation of a communication session (New OpenETCS Requirement Type)

##### 1579: Tabelle (New OpenETCS Requirement Type)

###### 1580: Zeile (New OpenETCS Requirement Type)

###### 1581 (New OpenETCS Requirement Type)
Field No.

###### 1582 (New OpenETCS Requirement Type)
VARIABLE

###### 1583 (New OpenETCS Requirement Type)
Remarks

###### 1584: Zeile (New OpenETCS Requirement Type)

###### 1585 (New OpenETCS Requirement Type)

###### 1586 (New OpenETCS Requirement Type)

###### 1587 (New OpenETCS Requirement Type)

###### 1588: Zeile (New OpenETCS Requirement Type)

###### 1589 (New OpenETCS Requirement Type)

###### 1590 (New OpenETCS Requirement Type)
NID_MESSAGE

###### 1591 (New OpenETCS Requirement Type)

###### 1592: Zeile (New OpenETCS Requirement Type)

###### 1593 (New OpenETCS Requirement Type)

###### 1594 (New OpenETCS Requirement Type)
L_MESSAGE

###### 1595 (New OpenETCS Requirement Type)

###### 1596: Zeile (New OpenETCS Requirement Type)

###### 1597 (New OpenETCS Requirement Type)

###### 1598 (New OpenETCS Requirement Type)
T_TRAIN

###### 1599 (New OpenETCS Requirement Type)
always set to unknown

###### 1600: Zeile (New OpenETCS Requirement Type)

###### 1601 (New OpenETCS Requirement Type)

###### 1602 (New OpenETCS Requirement Type)
M_ACK

###### 1603 (New OpenETCS Requirement Type)

###### 1604: Zeile (New OpenETCS Requirement Type)

###### 1605 (New OpenETCS Requirement Type)

###### 1606 (New OpenETCS Requirement Type)
NID_LRBG

###### 1607 (New OpenETCS Requirement Type)
always set to unknown

#### 1608: 8.7.17 Message 39: Acknowledgement of termination of a communication session (New OpenETCS Requirement Type)

##### 1609: Tabelle (New OpenETCS Requirement Type)

###### 1610: Zeile (New OpenETCS Requirement Type)

###### 1611 (New OpenETCS Requirement Type)
Field No.

###### 1612 (New OpenETCS Requirement Type)
VARIABLE

###### 1613 (New OpenETCS Requirement Type)
Remarks

###### 1614: Zeile (New OpenETCS Requirement Type)

###### 1615 (New OpenETCS Requirement Type)

###### 1616 (New OpenETCS Requirement Type)
NID_MESSAGE

###### 1617 (New OpenETCS Requirement Type)

###### 1618: Zeile (New OpenETCS Requirement Type)

###### 1619 (New OpenETCS Requirement Type)

###### 1620 (New OpenETCS Requirement Type)
L_MESSAGE

###### 1621 (New OpenETCS Requirement Type)

###### 1622: Zeile (New OpenETCS Requirement Type)

###### 1623 (New OpenETCS Requirement Type)

###### 1624 (New OpenETCS Requirement Type)
T_TRAIN

###### 1625 (New OpenETCS Requirement Type)

###### 1626: Zeile (New OpenETCS Requirement Type)

###### 1627 (New OpenETCS Requirement Type)

###### 1628 (New OpenETCS Requirement Type)
M_ACK

###### 1629 (New OpenETCS Requirement Type)
always set to 0

###### 1630: Zeile (New OpenETCS Requirement Type)

###### 1631 (New OpenETCS Requirement Type)

###### 1632 (New OpenETCS Requirement Type)
NID_LRBG

###### 1633 (New OpenETCS Requirement Type)

#### 1634: 8.7.18 Message 40: Train Rejected (New OpenETCS Requirement Type)

##### 1635: Tabelle (New OpenETCS Requirement Type)

###### 1636: Zeile (New OpenETCS Requirement Type)

###### 1637 (New OpenETCS Requirement Type)
Field No.

###### 1638 (New OpenETCS Requirement Type)
VARIABLE

###### 1639 (New OpenETCS Requirement Type)
Remarks

###### 1640: Zeile (New OpenETCS Requirement Type)

###### 1641 (New OpenETCS Requirement Type)

###### 1642 (New OpenETCS Requirement Type)
NID_MESSAGE

###### 1643 (New OpenETCS Requirement Type)

###### 1644: Zeile (New OpenETCS Requirement Type)

###### 1645 (New OpenETCS Requirement Type)

###### 1646 (New OpenETCS Requirement Type)
L_MESSAGE

###### 1647 (New OpenETCS Requirement Type)

###### 1648: Zeile (New OpenETCS Requirement Type)

###### 1649 (New OpenETCS Requirement Type)

###### 1650 (New OpenETCS Requirement Type)
T_TRAIN

###### 1651 (New OpenETCS Requirement Type)

###### 1652: Zeile (New OpenETCS Requirement Type)

###### 1653 (New OpenETCS Requirement Type)

###### 1654 (New OpenETCS Requirement Type)
M_ACK

###### 1655 (New OpenETCS Requirement Type)

###### 1656: Zeile (New OpenETCS Requirement Type)

###### 1657 (New OpenETCS Requirement Type)

###### 1658 (New OpenETCS Requirement Type)
NID_LRBG

###### 1659 (New OpenETCS Requirement Type)

#### 1660: 8.7.19 Message 41: Train Accepted (New OpenETCS Requirement Type)

##### 1661: Tabelle (New OpenETCS Requirement Type)

###### 1662: Zeile (New OpenETCS Requirement Type)

###### 1663 (New OpenETCS Requirement Type)
Field No.

###### 1664 (New OpenETCS Requirement Type)
VARIABLE

###### 1665 (New OpenETCS Requirement Type)
Remarks

###### 1666: Zeile (New OpenETCS Requirement Type)

###### 1667 (New OpenETCS Requirement Type)

###### 1668 (New OpenETCS Requirement Type)
NID_MESSAGE

###### 1669 (New OpenETCS Requirement Type)

###### 1670: Zeile (New OpenETCS Requirement Type)

###### 1671 (New OpenETCS Requirement Type)

###### 1672 (New OpenETCS Requirement Type)
L_MESSAGE

###### 1673 (New OpenETCS Requirement Type)

###### 1674: Zeile (New OpenETCS Requirement Type)

###### 1675 (New OpenETCS Requirement Type)

###### 1676 (New OpenETCS Requirement Type)
T_TRAIN

###### 1677 (New OpenETCS Requirement Type)

###### 1678: Zeile (New OpenETCS Requirement Type)

###### 1679 (New OpenETCS Requirement Type)

###### 1680 (New OpenETCS Requirement Type)
M_ACK

###### 1681 (New OpenETCS Requirement Type)

###### 1682: Zeile (New OpenETCS Requirement Type)

###### 1683 (New OpenETCS Requirement Type)

###### 1684 (New OpenETCS Requirement Type)
NID_LRBG

###### 1685 (New OpenETCS Requirement Type)

#### 1686: 8.7.20 Intentionally deleted (New OpenETCS Requirement Type)

#### 1687: 8.7.21 Message 43: SoM position report confirmed by RBC (New OpenETCS Requirement Type)

##### 1688: Tabelle (New OpenETCS Requirement Type)

###### 1689: Zeile (New OpenETCS Requirement Type)

###### 1690 (New OpenETCS Requirement Type)
Field No.

###### 1691 (New OpenETCS Requirement Type)
VARIABLE

###### 1692 (New OpenETCS Requirement Type)
Remarks

###### 1693: Zeile (New OpenETCS Requirement Type)

###### 1694 (New OpenETCS Requirement Type)

###### 1695 (New OpenETCS Requirement Type)
NID_MESSAGE

###### 1696 (New OpenETCS Requirement Type)

###### 1697: Zeile (New OpenETCS Requirement Type)

###### 1698 (New OpenETCS Requirement Type)

###### 1699 (New OpenETCS Requirement Type)
L_MESSAGE

###### 1700 (New OpenETCS Requirement Type)

###### 1701: Zeile (New OpenETCS Requirement Type)

###### 1702 (New OpenETCS Requirement Type)

###### 1703 (New OpenETCS Requirement Type)
T_TRAIN

###### 1704 (New OpenETCS Requirement Type)

###### 1705: Zeile (New OpenETCS Requirement Type)

###### 1706 (New OpenETCS Requirement Type)

###### 1707 (New OpenETCS Requirement Type)
M_ACK

###### 1708 (New OpenETCS Requirement Type)

###### 1709: Zeile (New OpenETCS Requirement Type)

###### 1710 (New OpenETCS Requirement Type)

###### 1711 (New OpenETCS Requirement Type)
NID_LRBG

###### 1712 (New OpenETCS Requirement Type)

#### 1713: 8.7.22 Message 45: Assignment of coordinate system (New OpenETCS Requirement Type)

##### 1714: Tabelle (New OpenETCS Requirement Type)

###### 1715: Zeile (New OpenETCS Requirement Type)

###### 1716 (New OpenETCS Requirement Type)
Field No.

###### 1717 (New OpenETCS Requirement Type)
VARIABLE

###### 1718 (New OpenETCS Requirement Type)
Remarks

###### 1719: Zeile (New OpenETCS Requirement Type)

###### 1720 (New OpenETCS Requirement Type)
1

###### 1721 (New OpenETCS Requirement Type)
NID_MESSAGE

###### 1722 (New OpenETCS Requirement Type)

###### 1723: Zeile (New OpenETCS Requirement Type)

###### 1724 (New OpenETCS Requirement Type)
2

###### 1725 (New OpenETCS Requirement Type)
L_MESSAGE

###### 1726 (New OpenETCS Requirement Type)

###### 1727: Zeile (New OpenETCS Requirement Type)

###### 1728 (New OpenETCS Requirement Type)
3

###### 1729 (New OpenETCS Requirement Type)
T_TRAIN

###### 1730 (New OpenETCS Requirement Type)

###### 1731: Zeile (New OpenETCS Requirement Type)

###### 1732 (New OpenETCS Requirement Type)
4

###### 1733 (New OpenETCS Requirement Type)
M_ACK

###### 1734 (New OpenETCS Requirement Type)

###### 1735: Zeile (New OpenETCS Requirement Type)

###### 1736 (New OpenETCS Requirement Type)
5

###### 1737 (New OpenETCS Requirement Type)
NID_LRBG

###### 1738 (New OpenETCS Requirement Type)

###### 1739: Zeile (New OpenETCS Requirement Type)

###### 1740 (New OpenETCS Requirement Type)
6

###### 1741 (New OpenETCS Requirement Type)
Q_ORIENTATION

###### 1742 (New OpenETCS Requirement Type)

## R1 (Proxy Type)
platform:/resource/model/sysml/dataDictionary/DataDictionary.uml#_PAR7cLWYEeOFuO01m4XL1Q
<Data Type> EurobaliseTelegram / <Model> Eurobalise_Interface_(BTM) / <Model> API_Services
isAbstract=false
isFinalSpecialization=false
isLeaf=[]
name=EurobaliseTelegram
qualifiedName=DataDictionaryModel::API_Services::Eurobalise_Interface_(BTM)::EurobaliseTelegram
visibility=public
