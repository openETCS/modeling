# Subset026

# Specification: Specification Document
- Description: Subset026

## 2
System Requirements Specification Chapter 2
Basic System Description
- atomic: true
- implement: false
- Legal Obligation: unknown
- kind: Heading
- WordTraceId: 26

### 2.1
Modification History
- atomic: false
- implement: true
- Legal Obligation: not applicable
- kind: ordinary
- WordTraceId: 292

### 2.1[2]
- atomic: false
- implement: false
- Legal Obligation: not applicable
- kind: Placeholder
- WordTraceId: 313

#### 2.1[2].[t]*
| Issue Number Date | Section Number | Modification / Description | Author |
| --- | --- | --- | --- |
| 0.0.1 19 july 1999 | All | First class 1 draft using new templates and including contributions from WPs | PZ |
| 0.1.0 26 july 1999 | System architecture figure § 2.3.1.2 | Updating and introduction of Radio infill Reference to future class 1 deleted | PZ |
| 1.0.0 29 July 1999 | Document version, editorial changes, updating the architecture figure. | Finalisation in Stuttgart 990729 | HE |
| 1.2.0 990730 | Version number | Release version | HE |
| 1.2.1 991209 | All | Draft for 2 nd release | SAB |
| 1.3.0 9912016 | All | Review comments added | SAB |
| 2.0.0 991222 | Minor editing | Finalisation | SAB |
| 2.0.1 | All | Corrections after review | SAB |
| 2.1.0 | Minor editing | UNISIG release | SAB |
| 2.2.0 | Version number | UNISIG release | SAB |
| 2.2.2 1.2.2002 | Version number | Final edition | Ch. Frerichs |
| 2.3.0 24/02/06 | Version number No change since 2.2.2 | Release version | HK |
- atomic: false
- implement: false
- Legal Obligation: not applicable
- kind: Table
- WordTraceId: 1185

### 2.2
Table of Contents
- atomic: false
- implement: true
- Legal Obligation: not applicable
- kind: ordinary
- WordTraceId: 1186

### 2.3
Introduction
- atomic: false
- implement: false
- Legal Obligation: not applicable
- kind: Heading
- WordTraceId: 2254

#### 2.3.1
Scope and purpose
- atomic: false
- implement: false
- Legal Obligation: not applicable
- kind: Heading
- WordTraceId: 2267

##### 2.3.1.1
The present chapter gives the basic description of the
system
proposed to satisfy the mandatory functional requirements of the Function Requirements Specification Version 4.3.
- atomic: true
- implement: true
- Legal Obligation: unknown
- kind: ordinary
- WordTraceId: 2285

### 2.4
System structure
- atomic: false
- implement: false
- Legal Obligation: not applicable
- kind: Heading
- WordTraceId: 2462

#### 2.4.1
PLACEHOLDER REQUIREMENT - DO NOT TRACE
- atomic: false
- implement: false
- Legal Obligation: not applicable
- kind: Placeholder
- WordTraceId: 2479

##### 2.4.1.1
Due to the nature of the required functions, the
ERTMS/ETCS system
will have to be partly on the trackside and partly on board the trains.
- implementerEnhanced: Due to the nature of the required functions, the ERTMS/ETCS system will have to be partly on the
  trackside
  [EXTERNAL]
  and partly on board the trains.
- atomic: true
- implement: true
- Legal Obligation: unknown
- kind: ordinary
- WordTraceId: 2479

##### 2.4.1.2
This defines two sub-systems, the on-board sub-system and the trackside sub-system.
- implementerEnhanced: This defines two sub-systems, the on-board sub-system and the
  trackside
  [EXTERNAL]
  sub-system.
- atomic: true
- implement: false
- Legal Obligation: unknown
- kind: Definition
- WordTraceId: 2619

##### 2.4.1.3
The environment of ERTMS/ETCS system is composed of:
- atomic: true
- implement: false
- Legal Obligation: unknown
- kind: Heading
- WordTraceId: 2703

###### 2.4.1.3.a
the train, which will then be considered in the train interface specification;
- atomic: true
- implement: true
- Legal Obligation: unknown
- kind: ordinary
- ListNumberText: a)
- WordTraceId: 2756

###### 2.4.1.3.b
the driver, which will then be considered via the driver interface specification;
- implementerEnhanced: the
  driver
  [EXTERNAL]
  , which will then be considered via the
  driver
  [EXTERNAL]
  interface specification;
- atomic: true
- implement: true
- Legal Obligation: unknown
- kind: ordinary
- ListNumberText: b)
- WordTraceId: 2835

###### 2.4.1.3.c
other onboard interfaces (see architecture drawing in 2.5.3),
- atomic: true
- implement: true
- Legal Obligation: unknown
- kind: ordinary
- ListNumberText: c)
- WordTraceId: 2917
- CrossRefLink -> 2.5.3

###### 2.4.1.3.d
external trackside systems (interlockings, control centres, etc.), for which no interoperability requirement will be established.
- implementerEnhanced: external
  [EXTERNAL]
  trackside
  [EXTERNAL]
  systems (interlockings, control centres,
  etc.
  [WEAK]
  ), for which no interoperability requirement will be established.
- atomic: true
- implement: true
- Legal Obligation: unknown
- kind: ordinary
- ListNumberText: d)
- WordTraceId: 2979

### 2.5
Sub-systems
- atomic: false
- implement: false
- Legal Obligation: not applicable
- kind: Heading
- WordTraceId: 3110

#### 2.5.1
Trackside subsystem
- implementerEnhanced: Trackside
  [EXTERNAL]
  subsystem
- atomic: false
- implement: false
- Legal Obligation: not applicable
- kind: Heading
- WordTraceId: 3122

##### 2.5.1.1
Depending of the application level (see further sections), the trackside sub-system can be composed of:
- implementerEnhanced: Depending of the application level (see further sections), the
  trackside
  [EXTERNAL]
  sub-system can be composed of:
- atomic: true
- implement: false
- Legal Obligation: unknown
- kind: Heading
- WordTraceId: 3142

###### 2.5.1.1.a
balise
- implementerEnhanced: balise
  [EXTERNAL]
- atomic: true
- implement: true
- Legal Obligation: unknown
- kind: ordinary
- ListNumberText: a)
- WordTraceId: 3246

###### 2.5.1.1.b
lineside electronic unit
- implementerEnhanced: lineside electronic unit
  [EXTERNAL]
- atomic: true
- implement: true
- Legal Obligation: unknown
- kind: ordinary
- ListNumberText: b)
- WordTraceId: 3253

###### 2.5.1.1.c
the radio communication network (GSM-R)
- atomic: true
- implement: true
- Legal Obligation: unknown
- kind: ordinary
- ListNumberText: c)
- WordTraceId: 3278

###### 2.5.1.1.d
the Radio Block Centre (RBC)
- implementerEnhanced: the
  Radio Block Centre
  [EXTERNAL]
  (
  RBC
  [EXTERNAL]
  )
- atomic: true
- implement: true
- Legal Obligation: unknown
- kind: ordinary
- ListNumberText: d)
- WordTraceId: 3318

###### 2.5.1.1.e
Euroloop
- implementerEnhanced: Euroloop
  [EXTERNAL]
- atomic: true
- implement: true
- Legal Obligation: unknown
- kind: ordinary
- ListNumberText: e)
- WordTraceId: 3347

###### 2.5.1.1.f
Radio infill unit
- implementerEnhanced: Radio infill unit
  [EXTERNAL]
- atomic: true
- implement: true
- Legal Obligation: unknown
- kind: ordinary
- ListNumberText: f)
- WordTraceId: 3356

##### 2.5.1.2
Balise
- implementerEnhanced: Balise
  [EXTERNAL]
- atomic: false
- implement: false
- Legal Obligation: not applicable
- kind: Heading
- WordTraceId: 3374

###### 2.5.1.2.1
The balise is a transmission devices that can send telegrams to the on-board sub-system.
- implementerEnhanced: The
  balise
  [EXTERNAL]
  is a transmission devices that can send telegrams to the on-board sub-system.
- atomic: true
- implement: true
- Legal Obligation: unknown
- kind: ordinary
- WordTraceId: 3381

###### 2.5.1.2.2
The balise is based on the existing Eurobalise specifications. These documents are included in the frame of the ERTMS/ETCS Class 1 specifications.
- implementerEnhanced: The
  balise
  [EXTERNAL]
  is based on the existing
  Eurobalise
  [EXTERNAL]
  specifications. These documents are included in the frame of the ERTMS/ETCS Class 1 specifications.
- atomic: false
- implement: true
- Legal Obligation: unknown
- kind: ordinary
- WordTraceId: 3470

###### 2.5.1.2.3
The balises provides the up-link, i. e. the possibility to send messages from trackside to the on-board sub-system.
- implementerEnhanced: The
  balises
  [EXTERNAL]
  provides the up-link, i. e. the possibility to send messages from
  trackside
  [EXTERNAL]
  to the on-board sub-system.
- atomic: true
- implement: true
- Legal Obligation: unknown
- kind: ordinary
- WordTraceId: 3617

###### 2.5.1.2.4
The balises can provide fixed messages or, when connected to a lineside electronic unit, messages that can be changed.
- implementerEnhanced: The
  balises
  [EXTERNAL]
  can provide fixed messages or,
  when
  [CONDITION]
  connected to a
  lineside electronic unit
  [EXTERNAL]
  , messages that can be changed.
- atomic: true
- implement: true
- Legal Obligation: unknown
- kind: ordinary
- WordTraceId: 3733

###### 2.5.1.2.5
The balises will be organised in groups, each balise transmitting a telegram and the combination of all telegrams defining the message sent by the balise group.
- implementerEnhanced: The
  balises
  [EXTERNAL]
  will be organised in groups, each
  balise
  [EXTERNAL]
  transmitting a telegram and the combination of all telegrams defining the message sent by the
  balise group
  [EXTERNAL]
  .
- atomic: true
- implement: true
- Legal Obligation: unknown
- kind: ordinary
- WordTraceId: 3853

##### 2.5.1.3
Lineside electronic unit
- implementerEnhanced: Lineside electronic unit
  [EXTERNAL]
- atomic: false
- implement: false
- Legal Obligation: not applicable
- kind: Heading
- WordTraceId: 4014

###### 2.5.1.3.1
The lineside electronic units are electronic devices, that generate telegrams to be sent by balises, on basis of information received from external trackside systems.
- implementerEnhanced: The lineside electronic units are electronic devices, that generate telegrams to be sent by
  balises
  [EXTERNAL]
  , on basis of information received from
  external
  [EXTERNAL]
  trackside
  [EXTERNAL]
  systems.
- atomic: true
- implement: true
- Legal Obligation: unknown
- kind: ordinary
- WordTraceId: 4039

##### 2.5.1.4
Trackside radio communication network (GSM-R)
- implementerEnhanced: Trackside
  [EXTERNAL]
  radio communication network (GSM-R)
- atomic: false
- implement: false
- Legal Obligation: not applicable
- kind: Heading
- WordTraceId: 4206

###### 2.5.1.4.1
The GSM-R radio communication network is used for the bi-directional exchange of messages between on-board sub-systems and RBC or radio infill units.
- implementerEnhanced: The GSM-R radio communication network is used for the bi-directional exchange of messages between on-board sub-systems and
  RBC
  [EXTERNAL]
  or radio infill units.
- atomic: true
- implement: true
- Legal Obligation: unknown
- kind: ordinary
- WordTraceId: 4252

###### 2.5.1.4.2
The GSM Radio system is neither developed nor standardised within the frame of the ERTMS/ETCS Class 1 specifications. ERTMS/ETCS Class 1 uses the interfaces as specified in the EIRENE/MORANE specifications [UNISIG Reference documents, SUBSET-008, SUBSET-052].
- atomic: false
- implement: true
- Legal Obligation: unknown
- kind: ordinary
- WordTraceId: 4403

##### 2.5.1.5
RBC
- implementerEnhanced: RBC
  [EXTERNAL]
- atomic: false
- implement: false
- Legal Obligation: not applicable
- kind: Heading
- WordTraceId: 4664

###### 2.5.1.5.1
The RBC is a computer-based system that elaborates messages to be sent to the train on basis of information received from external trackside systems and on basis of information exchanged with the on-board sub-systems.
- implementerEnhanced: The
  RBC
  [EXTERNAL]
  is a computer-based system that elaborates messages to be sent to the train on basis of information received from
  external
  [EXTERNAL]
  trackside
  [EXTERNAL]
  systems and on basis of information exchanged with the on-board sub-systems.
- atomic: true
- implement: true
- Legal Obligation: unknown
- kind: ordinary
- WordTraceId: 4668

###### 2.5.1.5.2
The main objective of these messages is to provide movement authorities to allow the safe movement of trains on the Railway infrastructure area under the responsibility of the RBC.
- implementerEnhanced: The main objective of these messages is to provide movement authorities to allow the safe movement of trains on the Railway infrastructure area under the responsibility of the
  RBC
  [EXTERNAL]
  .
- atomic: true
- implement: true
- Legal Obligation: unknown
- kind: ordinary
- WordTraceId: 4887

###### 2.5.1.5.3
The interoperability requirements for the RBC are mainly related to the data exchange between the RBC and the on-board sub-system.
- implementerEnhanced: The interoperability requirements for the
  RBC
  [EXTERNAL]
  are mainly related to the data exchange between the
  RBC
  [EXTERNAL]
  and the on-board sub-system.
- atomic: true
- implement: true
- Legal Obligation: unknown
- kind: ordinary
- WordTraceId: 5068

##### 2.5.1.6
Euroloop
- implementerEnhanced: Euroloop
  [EXTERNAL]
- atomic: false
- implement: false
- Legal Obligation: not applicable
- kind: Heading
- WordTraceId: 5199

###### 2.5.1.6.1
The Euroloop subsystem operates on Level 1 lines, providing signalling information in advance as regard to the next main signal in the train running direction.
- implementerEnhanced: The
  Euroloop
  [EXTERNAL]
  subsystem operates on Level 1 lines, providing signalling information in advance as regard to the next main signal in the train running direction.
- atomic: true
- implement: true
- Legal Obligation: unknown
- kind: ordinary
- WordTraceId: 5208

###### 2.5.1.6.2
The Euroloop subsystem is composed of an on-board functionality and by one or more trackside parts.
- implementerEnhanced: The
  Euroloop
  [EXTERNAL]
  subsystem is composed of an on-board functionality and by one or more
  trackside
  [EXTERNAL]
  parts.
- atomic: true
- implement: true
- Legal Obligation: unknown
- kind: ordinary
- WordTraceId: 5368

##### 2.5.1.7
Radio in-fill Unit
- implementerEnhanced: Radio in-fill Unit
  [EXTERNAL]
- atomic: false
- implement: false
- Legal Obligation: not applicable
- kind: Heading
- WordTraceId: 5469

###### 2.5.1.7.1
The RADIO IN-FILL subsystem operates on Level 1 lines, providing signalling information in advance as regard to the next main signal in the train running direction.
- atomic: true
- implement: true
- Legal Obligation: unknown
- kind: ordinary
- WordTraceId: 5488

###### 2.5.1.7.2
The RADIO IN-FILL subsystem is composed of an on-board functionality and by one or more trackside parts (named RADIO IN-FILL Unit).
- implementerEnhanced: The RADIO IN-FILL subsystem is composed of an on-board functionality and by one or more
  trackside
  [EXTERNAL]
  parts (named
  RADIO IN-FILL Unit
  [EXTERNAL]
  ).
- atomic: true
- implement: true
- Legal Obligation: unknown
- kind: ordinary
- WordTraceId: 5653

#### 2.5.2
On-board sub-system
- atomic: false
- implement: false
- Legal Obligation: not applicable
- kind: Heading
- WordTraceId: 5786

##### 2.5.2.1
Depending of the application level (see further sections), the on-board sub-system can be composed of:
- atomic: true
- implement: false
- Legal Obligation: unknown
- kind: Heading
- WordTraceId: 5806

###### 2.5.2.1.a
the ERTMS/ETCS on-board equipment;
- implementerEnhanced: the
  ERTMS/ETCS on-board equipment
  [SELF]
  ;
- atomic: true
- implement: true
- Legal Obligation: unknown
- kind: ordinary
- ListNumberText: a)
- WordTraceId: 5909

###### 2.5.2.1.b
the on-board part of the GSM-R radio system;
- atomic: true
- implement: true
- Legal Obligation: unknown
- kind: ordinary
- ListNumberText: b)
- WordTraceId: 5944

###### 2.5.2.1.c
specific transmission modules for existing national train control systems.
- atomic: true
- implement: true
- Legal Obligation: unknown
- kind: ordinary
- ListNumberText: c)
- WordTraceId: 5990

##### 2.5.2.2
ERTMS/ETCS on-board equipment
- implementerEnhanced: ERTMS/ETCS on-board equipment
  [SELF]
- atomic: false
- implement: false
- Legal Obligation: not applicable
- kind: Heading
- WordTraceId: 6065

###### 2.5.2.2.1
The ERTMS/ETCS on-board equipment is a computer-based system that supervises the movement of the train to which it belongs, on basis of information exchanged with the trackside sub-system.
- implementerEnhanced: The
  ERTMS/ETCS on-board equipment
  [SELF]
  is a computer-based system that supervises the movement of the train to which it belongs, on basis of information exchanged with the
  trackside
  [EXTERNAL]
  sub-system.
- atomic: true
- implement: true
- Legal Obligation: unknown
- kind: ordinary
- WordTraceId: 6095

###### 2.5.2.2.2
The interoperability requirements for the ERTMS/ETCS on-board equipment are related to the functionality and the data exchange between the trackside sub-systems and the on-board sub-system and to the functional data exchange between the on-board sub-system and:
- implementerEnhanced: The interoperability requirements for the
  ERTMS/ETCS on-board equipment
  [SELF]
  are related to the functionality and the data exchange between the
  trackside
  [EXTERNAL]
  sub-systems and the on-board sub-system and to the functional data exchange between the on-board sub-system and:
- atomic: true
- implement: false
- Legal Obligation: unknown
- kind: Heading
- WordTraceId: 6285

###### 2.5.2.2.2.a
the driver;
- implementerEnhanced: the
  driver
  [EXTERNAL]
  ;
- atomic: true
- implement: true
- Legal Obligation: unknown
- kind: ordinary
- ListNumberText: a)
- WordTraceId: 6547

###### 2.5.2.2.2.b
the train;
- atomic: true
- implement: true
- Legal Obligation: unknown
- kind: ordinary
- ListNumberText: b)
- WordTraceId: 6559

###### 2.5.2.2.2.c
the specific transmission modules (STM’s).
- atomic: true
- implement: true
- Legal Obligation: unknown
- kind: ordinary
- ListNumberText: c)
- WordTraceId: 6570

##### 2.5.2.3
Onboard radio communication system (GSM-R)
- atomic: false
- implement: false
- Legal Obligation: not applicable
- kind: Heading
- WordTraceId: 6613

###### 2.5.2.3.1
The GSM-R on-board radio system is used for the bi-directional exchange of messages between on-board sub-system and RBC or radio infill unit.
- implementerEnhanced: The GSM-R on-board radio system is used for the bi-directional exchange of messages between on-board sub-system and
  RBC
  [EXTERNAL]
  or
  radio infill unit
  [EXTERNAL]
  .
- atomic: true
- implement: true
- Legal Obligation: unknown
- kind: ordinary
- WordTraceId: 6656

###### 2.5.2.3.2
The GSM Radio system is neither developed nor standardised within the frame of the UNISIG requirements specifications [UNISIG Reference documents, SUBSET-008].
- atomic: true
- implement: true
- Legal Obligation: unknown
- kind: ordinary
- WordTraceId: 6799

#### 2.5.3
UNISIG ERTMS/ETCS reference architecture
- atomic: false
- implement: true
- Legal Obligation: not applicable
- kind: ordinary
- WordTraceId: 6959

#### 2.5.3[2]
- atomic: false
- implement: false
- Legal Obligation: not applicable
- kind: Placeholder
- WordTraceId: 7001

##### 2.5.3[2].[f]1
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- atomic: false
- implement: false
- Legal Obligation: not applicable
- kind: Figure
- WordTraceId: 7029

###### 2.5.3[2].[f]1.C
Figure {Figure 1}: ERTMS/ETCS system
- implementerEnhanced: Figure 1: ERTMS/ETCS system
- atomic: true
- PlainText: Figure 1: ERTMS/ETCS system
- implement: false
- Legal Obligation: unknown
- kind: Figure
- WordTraceId: 7029

##### 2.5.3[2].1
Note: Interfaces in brackets are not required for interoperability.
- atomic: false
- implement: false
- Legal Obligation: not applicable
- kind: Note
- ListNumberText: 2.5.3.1
- WordTraceId: 7082

### 2.6
Levels and transitions
- atomic: false
- implement: false
- Legal Obligation: not applicable
- kind: Heading
- WordTraceId: 7153

#### 2.6.1
Introduction
- atomic: false
- implement: false
- Legal Obligation: not applicable
- kind: Heading
- WordTraceId: 7176

##### 2.6.1.1
The different ERTMS/ETCS application levels (short: levels) are a way to express the possible operating relationships between track and train. Level definitions are principally related to the trackside equipment used, to the way trackside information reaches the on-board units and to which functions are processed in the trackside and in the on-board equipment respectively.
- implementerEnhanced: The different ERTMS/ETCS application levels (short: levels) are a way to express the possible operating relationships between track and train. Level definitions are principally related to the
  trackside
  [EXTERNAL]
  equipment used, to the way
  trackside
  [EXTERNAL]
  information reaches the on-board units and to which functions are processed in the
  trackside
  [EXTERNAL]
  and in the
  on-board equipment
  [SELF]
  respectively.
- atomic: false
- implement: true
- Legal Obligation: unknown
- kind: ordinary
- WordTraceId: 7189

##### 2.6.1.2
Different levels have been defined to allow each individual railway administration to select the appropriate ERTMS/ETCS application trackside, according to their strategies, to their trackside infrastructure and to the required performance. Furthermore, the different application levels permit the interfacing of individual signalling systems and train control systems to ERTMS/ETCS.
- implementerEnhanced: Different levels have been defined to allow each individual railway administration to select the appropriate ERTMS/ETCS application
  trackside
  [EXTERNAL]
  , according to their strategies, to their
  trackside
  [EXTERNAL]
  infrastructure and to the required performance. Furthermore, the different application levels permit the interfacing of individual signalling systems and train control systems to ERTMS/ETCS.
- atomic: false
- implement: true
- Legal Obligation: unknown
- kind: ordinary
- WordTraceId: 7566

##### 2.6.1.3
For the purpose of a consistent specification a level 0 has been defined. This level is used for operation on non-equipped (unfitted) lines or on lines, which are in commissioning.
- atomic: false
- implement: true
- Legal Obligation: unknown
- kind: ordinary
- WordTraceId: 7950

#### 2.6.2
Definitions
- atomic: false
- implement: false
- Legal Obligation: not applicable
- kind: Heading
- WordTraceId: 8132

##### 2.6.2.1
A train equipped with ERTMS/ETCS on-board equipment always co-operates with the ERTMS/ETCS trackside equipment in a defined ERTMS/ETCS level.
- implementerEnhanced: A train equipped with
  ERTMS/ETCS on-board equipment
  [SELF]
  always co-operates with the ERTMS/ETCS
  trackside
  [EXTERNAL]
  equipment in a defined ERTMS/ETCS level.
- atomic: true
- implement: true
- Legal Obligation: unknown
- kind: ordinary
- WordTraceId: 8144

##### 2.6.2.2
All transitions between levels are performed according to well-specified rules.
- atomic: true
- implement: true
- Legal Obligation: unknown
- kind: ordinary
- WordTraceId: 8287

##### 2.6.2.3
ERTMS/ETCS can be configured to operate in one of the following application levels:
- atomic: true
- implement: false
- Legal Obligation: unknown
- kind: Heading
- WordTraceId: 8368

###### 2.6.2.3.*[1]
ERTMS/ETCS Level 0 (train equipped with ERTMS/ETCS operating on a line without ERTMS/ETCS or national system or with the ERTMS/ETCS systems in commissioning)
- implementerEnhanced: ERTMS/ETCS Level 0 (train equipped with ERTMS/ETCS operating on a line without ERTMS/ETCS or
  national system
  [EXTERNAL]
  or with the ERTMS/ETCS systems in commissioning)
- atomic: true
- implement: true
- Legal Obligation: unknown
- kind: ordinary
- ListNumberText: ·
- WordTraceId: 8453

###### 2.6.2.3.*[2]
ERTMS/ETCS Level STM (train equipped with ERTMS/ETCS operating on a line equipped with a national system to which it interfaces by use of an STM)
- implementerEnhanced: ERTMS/ETCS Level STM (train equipped with ERTMS/ETCS operating on a line equipped with a
  national system
  [EXTERNAL]
  to which it interfaces by use of an STM)
- atomic: true
- implement: true
- Legal Obligation: unknown
- kind: ordinary
- ListNumberText: ·
- WordTraceId: 8611

###### 2.6.2.3.*[3]
ERTMS/ETCS Application Level 1 with or without infill transmission (train equipped with ERTMS/ETCS operating on a line equipped with Eurobalises and optionally Euroloop or Radio infill)
- implementerEnhanced: ERTMS/ETCS Application Level 1 with or without infill transmission (train equipped with ERTMS/ETCS operating on a line equipped with
  Eurobalises
  [EXTERNAL]
  and optionally
  Euroloop
  [EXTERNAL]
  or Radio infill)
- atomic: true
- implement: true
- Legal Obligation: unknown
- kind: ordinary
- ListNumberText: ·
- WordTraceId: 8757

###### 2.6.2.3.*[4]
ERTMS/ETCS Application Level 2 (train equipped with ERTMS/ETCS operating on a line controlled by a Radio Block Centre and equipped with Eurobalises and Euroradio) with train location and train integrity proving performed by the trackside
- implementerEnhanced: ERTMS/ETCS Application Level 2 (train equipped with ERTMS/ETCS operating on a line controlled by a
  Radio Block Centre
  [EXTERNAL]
  and equipped with
  Eurobalises
  [EXTERNAL]
  and Euroradio) with train location and train integrity proving performed by the
  trackside
  [EXTERNAL]
- atomic: true
- implement: true
- Legal Obligation: unknown
- kind: ordinary
- ListNumberText: ·
- WordTraceId: 8943

###### 2.6.2.3.*[5]
ERTMS/ETCS Application Level 3 (similar to level 2 but with train location and train integrity supervision based on information received from the train)
- atomic: true
- implement: true
- Legal Obligation: unknown
- kind: ordinary
- ListNumberText: ·
- WordTraceId: 9181

##### 2.6.2.4
It is possible to superimpose several application levels in parallel on the same track, for example to run trains without train integrity device in level 2 and in parallel trains equipped with train integrity device in level 3. Other examples might be a station which is shared by trains arriving over level 1 and level 2 lines (junctions) or parallel operation of a national system with ERTMS/ETCS. Mixed levels are supported.
- implementerEnhanced: It is possible to superimpose several application levels in parallel on the same track,
  for example
  [WEAK]
  to run trains without train integrity device in level 2 and in parallel trains equipped with train integrity device in level 3. Other examples might be a station which is shared by trains arriving over level 1 and level 2 lines (junctions) or parallel operation of a
  national system
  [EXTERNAL]
  with ERTMS/ETCS. Mixed levels are supported.
- atomic: false
- implement: true
- Legal Obligation: unknown
- kind: ordinary
- WordTraceId: 9335

##### 2.6.2.5
Levels 1, 2 and 3 are downwards compatible. This means that a level 3 equipped train is able to operate in level 1 and 2 and a level 2 equipped train in level 1.
- atomic: false
- implement: true
- Legal Obligation: unknown
- kind: ordinary
- WordTraceId: 9763

##### 2.6.2.6
Note: Operation under STM is not part of the downward compatibility chain.
- atomic: false
- implement: false
- Legal Obligation: not applicable
- kind: Note
- WordTraceId: 9926

##### 2.6.2.7
It is possible to transmit information not intended for ERTMS/ETCS but for other systems over the ERTMS/ETCS transmission channels. This information is ignored by ERTMS/ETCS.
- atomic: false
- implement: true
- Legal Obligation: unknown
- kind: ordinary
- WordTraceId: 10001

#### 2.6.3
ERTMS/ETCS Application Level 0
- atomic: false
- implement: false
- Legal Obligation: not applicable
- kind: Heading
- WordTraceId: 10177

##### 2.6.3.1
General description
- atomic: false
- implement: false
- Legal Obligation: not applicable
- kind: Heading
- WordTraceId: 10208

###### 2.6.3.1.1
Level 0 covers operation of ETCS equipped trains on lines not equipped with ETCS or national systems or on lines which are in commissioning, e.g. where trackside ERTMS/ETCS infrastructure may exist but has to be ignored.
- implementerEnhanced: Level 0 covers operation of ETCS equipped trains on lines not equipped with ETCS or national systems or on lines which are in commissioning,
  e.g.
  [WEAK]
  where
  trackside
  [EXTERNAL]
  ERTMS/ETCS infrastructure may exist but has to be ignored.
- atomic: true
- implement: true
- Legal Obligation: optional
- kind: ordinary
- WordTraceId: 10228

###### 2.6.3.1.2
In Level 0 line side optical signals or other means of signalling external to ERTMS/ETCS are used to give movement authorities to the driver.
- implementerEnhanced: In Level 0 line side optical signals or other means of signalling
  external
  [EXTERNAL]
  to ERTMS/ETCS are used to give movement authorities to the
  driver
  [EXTERNAL]
  .
- atomic: true
- implement: true
- Legal Obligation: unknown
- kind: ordinary
- WordTraceId: 10450

###### 2.6.3.1.3
ERTMS/ETCS on-board equipment provides no supervision except of the maximum design speed of a train and maximum speed permitted in unfitted areas.
- implementerEnhanced: ERTMS/ETCS on-board equipment
  [SELF]
  provides no supervision except of the maximum design speed of a train and maximum speed permitted in unfitted areas.
- atomic: true
- implement: true
- Legal Obligation: unknown
- kind: ordinary
- WordTraceId: 10593

###### 2.6.3.1.4
Train detection and train integrity supervision are performed by the trackside equipment of the underlying signalling system (interlocking, track circuits etc.) and are outside the scope of ERTMS/ETCS.
- implementerEnhanced: Train detection and train integrity supervision are performed by the
  trackside
  [EXTERNAL]
  equipment of the underlying signalling system (interlocking, track circuits
  etc.
  [WEAK]
  ) and are outside the scope of ERTMS/ETCS.
- atomic: true
- implement: true
- Legal Obligation: unknown
- kind: ordinary
- WordTraceId: 10741

###### 2.6.3.1.5
Level 0 uses no track-train transmission except Eurobalises to announce/command level transitions. Eurobalises therefore still have to be read. No balise data except certain special commands are interpreted.
- implementerEnhanced: Level 0 uses no track-train transmission except
  Eurobalises
  [EXTERNAL]
  to announce/command level transitions.
  Eurobalises
  [EXTERNAL]
  therefore still have to be read. No
  balise
  [EXTERNAL]
  data except certain special commands are interpreted.
- atomic: false
- implement: true
- Legal Obligation: unknown
- kind: ordinary
- WordTraceId: 10943

###### 2.6.3.1.6
No supervisory information is indicated on the driver MMI except the train speed. The maximum permitted speed is only displayed temporarily and on driver request. Train data has to be entered in order not to have to stop a train at a level transition to ERTMS/ETCS equipped area and to supervise maximum train speed.
- implementerEnhanced: No supervisory information is indicated on the
  driver
  [EXTERNAL]
  MMI except the train speed. The maximum permitted speed is only displayed
  temporarily
  [WEAK]
  and on
  driver
  [EXTERNAL]
  request. Train data has to be entered in order not to have to stop a train at a level transition to ERTMS/ETCS equipped area and to supervise maximum train speed.
- atomic: false
- implement: true
- Legal Obligation: unknown
- kind: ordinary
- WordTraceId: 11151

###### 2.6.3.1.6[2]
- atomic: false
- implement: false
- Legal Obligation: not applicable
- kind: Placeholder
- WordTraceId: 11468

###### 2.6.3.1.6[2].[f]2
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- atomic: false
- implement: false
- Legal Obligation: not applicable
- kind: Figure
- WordTraceId: 11470

###### 2.6.3.1.6[2].[f]2.C
Figure {Figure 2}: ERTMS/ETCS Application Level 0
- implementerEnhanced: Figure 2: ERTMS/ETCS Application Level 0
- atomic: true
- PlainText: Figure 2: ERTMS/ETCS Application Level 0
- implement: false
- Legal Obligation: unknown
- kind: Figure
- WordTraceId: 11470

##### 2.6.3.2
Summary of characteristics of Application Level 0
- atomic: false
- implement: false
- Legal Obligation: not applicable
- kind: Heading
- WordTraceId: 11536

###### 2.6.3.2.1
Trackside equipment:
- implementerEnhanced: Trackside
  [EXTERNAL]
  equipment:
- atomic: true
- implement: false
- Legal Obligation: unknown
- kind: Heading
- WordTraceId: 11586

###### 2.6.3.2.1.*[1]
No ERTMS/ETCS trackside equipment is used except for Eurobalises to announce level transitions and other specific commands.
- implementerEnhanced: No ERTMS/ETCS
  trackside
  [EXTERNAL]
  equipment is used except for
  Eurobalises
  [EXTERNAL]
  to announce level transitions and other specific commands.
- atomic: true
- implement: true
- Legal Obligation: unknown
- kind: ordinary
- ListNumberText: ·
- WordTraceId: 11608

###### 2.6.3.2.2
Main ERTMS/ETCS trackside functions:
- implementerEnhanced: Main ERTMS/ETCS
  trackside
  [EXTERNAL]
  functions:
- atomic: true
- implement: false
- Legal Obligation: unknown
- kind: Heading
- WordTraceId: 11732

###### 2.6.3.2.2.*[1]
None.
- atomic: true
- implement: true
- Legal Obligation: unknown
- kind: ordinary
- ListNumberText: ·
- WordTraceId: 11769

###### 2.6.3.2.3
On-board equipment:
- implementerEnhanced: On-board equipment
  [SELF]
  :
- atomic: true
- implement: false
- Legal Obligation: unknown
- kind: Heading
- WordTraceId: 11775

###### 2.6.3.2.3.*[1]
Onboard equipment with Eurobalise transmission.
- implementerEnhanced: Onboard equipment
  [SELF]
  with
  Eurobalise
  [EXTERNAL]
  transmission.
- atomic: true
- implement: true
- Legal Obligation: unknown
- kind: ordinary
- ListNumberText: ·
- WordTraceId: 11795

###### 2.6.3.2.4
Main ERTMS/ETCS on-board functions:
- implementerEnhanced: Main
  ERTMS/ETCS on-board
  [SELF]
  functions:
- atomic: true
- implement: false
- Legal Obligation: unknown
- kind: Heading
- WordTraceId: 11843

###### 2.6.3.2.4.*[1]
Supervision of maximum train speed.
- atomic: true
- implement: true
- Legal Obligation: unknown
- kind: ordinary
- ListNumberText: ·
- WordTraceId: 11879

###### 2.6.3.2.4.*[2]
Supervision of maximum speed permitted in an unfitted area.
- atomic: true
- implement: true
- Legal Obligation: unknown
- kind: ordinary
- ListNumberText: ·
- WordTraceId: 11915

###### 2.6.3.2.4.*[3]
Reading of Eurobalises to detect level transitions and certain special commands. All other messages are rejected.
- implementerEnhanced: Reading of
  Eurobalises
  [EXTERNAL]
  to detect level transitions and certain special commands. All other messages are rejected.
- atomic: false
- implement: true
- Legal Obligation: unknown
- kind: ordinary
- ListNumberText: ·
- WordTraceId: 11975

###### 2.6.3.2.4.*[4]
No cab signalling.
- atomic: true
- implement: true
- Legal Obligation: unknown
- kind: ordinary
- ListNumberText: ·
- WordTraceId: 12089

#### 2.6.4
ERTMS/ETCS Application Level STM
- atomic: false
- implement: false
- Legal Obligation: not applicable
- kind: Heading
- WordTraceId: 12109

##### 2.6.4.1
General description
- atomic: false
- implement: false
- Legal Obligation: not applicable
- kind: Heading
- WordTraceId: 12142

###### 2.6.4.1.1
Level STM is used to run ERTMS/ETCS equipped trains on lines equipped with national train control and speed supervision systems.
- atomic: true
- implement: true
- Legal Obligation: unknown
- kind: ordinary
- WordTraceId: 12162

###### 2.6.4.1.2
Train control information generated trackside by the national train control system is transmitted to the train via the communication channels of the underlying national system and transformed onboard into information interpretable by ERTMS/ETCS.
- implementerEnhanced: Train control information generated
  trackside
  [EXTERNAL]
  by the national train control system is transmitted to the train via the communication channels of the underlying
  national system
  [EXTERNAL]
  and transformed onboard into information interpretable by ERTMS/ETCS.
- atomic: true
- implement: true
- Legal Obligation: unknown
- kind: ordinary
- WordTraceId: 12292

###### 2.6.4.1.3
Note: Lineside optical signals might be necessary or not, depending on the performance and functionality of the underlying systems.
- atomic: false
- implement: false
- Legal Obligation: not applicable
- kind: Note
- WordTraceId: 12539

###### 2.6.4.1.4
The device which allows the ERTMS/ETCS onboard equipment to utilise the transmission system of the national system is called STM (specific transmission module).
- implementerEnhanced: The device which allows the
  ERTMS/ETCS onboard equipment
  [SELF]
  to utilise the transmission system of the
  national system
  [EXTERNAL]
  is called STM (specific transmission module).
- atomic: true
- implement: true
- Legal Obligation: unknown
- kind: ordinary
- WordTraceId: 12672

###### 2.6.4.1.5
The achievable level of supervision is similar to the one provided by the underlying national systems.
- atomic: true
- implement: true
- Legal Obligation: unknown
- kind: ordinary
- WordTraceId: 12834

###### 2.6.4.1.6
Train detection and train integrity supervision are performed by equipment external to ERTMS/ETCS.
- implementerEnhanced: Train detection and train integrity supervision are performed by equipment
  external
  [EXTERNAL]
  to ERTMS/ETCS.
- atomic: true
- implement: true
- Legal Obligation: unknown
- kind: ordinary
- WordTraceId: 12938

###### 2.6.4.1.7
Level STM uses no ERTMS/ETCS track-train transmission except to announce/command level transitions and specific commands related to balise transmission. Eurobalises therefore still have to be read. No data except level transition commands and certain special commands are interpreted.
- implementerEnhanced: Level STM uses no ERTMS/ETCS track-train transmission except to announce/command level transitions and specific commands related to
  balise
  [EXTERNAL]
  transmission.
  Eurobalises
  [EXTERNAL]
  therefore still have to be read. No data except level transition commands and certain special commands are interpreted.
- atomic: false
- implement: true
- Legal Obligation: unknown
- kind: ordinary
- WordTraceId: 13038

###### 2.6.4.1.8
The information displayed to the driver depends on the functionality of the underlying national system. The active STM is indicated to the driver as part of that information. Full train data has to be entered in order not to have to stop a train at a level transition position and to supervise maximum train speed.
- implementerEnhanced: The information displayed to the
  driver
  [EXTERNAL]
  depends on the functionality of the underlying
  national system
  [EXTERNAL]
  . The active STM is indicated to the
  driver
  [EXTERNAL]
  as part of that information. Full train data has to be entered in order not to have to stop a train at a level transition position and to supervise maximum train speed.
- atomic: false
- implement: true
- Legal Obligation: unknown
- kind: ordinary
- WordTraceId: 13324

###### 2.6.4.1.9
Each combination of national trackside systems shall be combined externally to the ERTMS/ETCS Onboard system and shall be regarded as one STM level.
- implementerEnhanced: Each combination of national
  trackside
  [EXTERNAL]
  systems shall be combined externally to the
  ERTMS/ETCS Onboard
  [SELF]
  system and shall be regarded as one STM level.
- atomic: false
- implement: false
- Legal Obligation: mandatory
- kind: Definition
- WordTraceId: 13639

###### 2.6.4.1.10
The reuse of ERTMS/ETCS Onboard functionality can be different depending on the configuration of a specific STM.
- implementerEnhanced: The reuse of
  ERTMS/ETCS Onboard
  [SELF]
  functionality can be different depending on the configuration of a specific STM.
- atomic: true
- implement: true
- Legal Obligation: unknown
- kind: ordinary
- WordTraceId: 13788

###### 2.6.4.1.11
Access to ERTMS/ETCS Onboard supervision functions is supported.
- implementerEnhanced: Access to
  ERTMS/ETCS Onboard
  [SELF]
  supervision functions is supported.
- atomic: true
- implement: true
- Legal Obligation: unknown
- kind: ordinary
- WordTraceId: 13901

###### 2.6.4.1.11[2]
- atomic: false
- implement: false
- Legal Obligation: not applicable
- kind: Placeholder
- WordTraceId: 13967

###### 2.6.4.1.11[2].[f]3
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- atomic: false
- implement: false
- Legal Obligation: not applicable
- kind: Figure
- WordTraceId: 13986

###### 2.6.4.1.11[2].[f]3.C
Figure {Figure 3}: ERTMS/ETCS Application Level STM
- implementerEnhanced: Figure 3: ERTMS/ETCS Application Level STM
- atomic: true
- implement: false
- Legal Obligation: unknown
- kind: Figure
- WordTraceId: 13986

##### 2.6.4.2
Summary of characteristics of Application Level STM
- atomic: false
- implement: false
- Legal Obligation: not applicable
- kind: Heading
- WordTraceId: 14054

###### 2.6.4.2.1
Trackside equipment:
- implementerEnhanced: Trackside
  [EXTERNAL]
  equipment:
- atomic: true
- implement: false
- Legal Obligation: unknown
- kind: Heading
- WordTraceId: 14106

###### 2.6.4.2.1.*[1]
Level STM uses the track-train transmission system from an underlying national system, which is not part of ERTMS/ETCS.
- implementerEnhanced: Level STM uses the track-train transmission system from an underlying
  national system
  [EXTERNAL]
  , which is not part of ERTMS/ETCS.
- atomic: true
- implement: true
- Legal Obligation: unknown
- kind: ordinary
- ListNumberText: ·
- WordTraceId: 14128

###### 2.6.4.2.1.*[2]
For level transition purposes Eurobalises are used.
- implementerEnhanced: For level transition purposes
  Eurobalises
  [EXTERNAL]
  are used.
- atomic: true
- implement: true
- Legal Obligation: unknown
- kind: ordinary
- ListNumberText: ·
- WordTraceId: 14248

###### 2.6.4.2.2
Main ERTMS/ETCS trackside functions:
- implementerEnhanced: Main ERTMS/ETCS
  trackside
  [EXTERNAL]
  functions:
- atomic: true
- implement: false
- Legal Obligation: unknown
- kind: Heading
- WordTraceId: 14300

###### 2.6.4.2.2.*[1]
None.
- atomic: true
- implement: true
- Legal Obligation: unknown
- kind: ordinary
- ListNumberText: ·
- WordTraceId: 14337

###### 2.6.4.2.3
On-board equipment:
- implementerEnhanced: On-board equipment
  [SELF]
  :
- atomic: true
- implement: false
- Legal Obligation: unknown
- kind: Heading
- WordTraceId: 14343

###### 2.6.4.2.3.*[1]
Onboard equipment with Eurobalise transmission.
- implementerEnhanced: Onboard equipment
  [SELF]
  with
  Eurobalise
  [EXTERNAL]
  transmission.
- atomic: true
- implement: true
- Legal Obligation: unknown
- kind: ordinary
- ListNumberText: ·
- WordTraceId: 14364

###### 2.6.4.2.3.*[2]
STM compatible with the respective national infrastructure.
- atomic: true
- implement: true
- Legal Obligation: unknown
- kind: ordinary
- ListNumberText: ·
- WordTraceId: 14412

###### 2.6.4.2.4
Main ERTMS/ETCS on-board function:
- implementerEnhanced: Main
  ERTMS/ETCS on-board
  [SELF]
  function:
- atomic: true
- implement: false
- Legal Obligation: unknown
- kind: Heading
- WordTraceId: 14472

###### 2.6.4.2.4.*[1]
Depending on national system and on STM implementation.
- implementerEnhanced: Depending on
  national system
  [EXTERNAL]
  and on STM implementation.
- atomic: true
- implement: true
- Legal Obligation: unknown
- kind: ordinary
- ListNumberText: ·
- WordTraceId: 14507

###### 2.6.4.2.4.*[2]
Reading of Eurobalises to detect level transitions and certain special commands. All other messages are rejected.
- implementerEnhanced: Reading of
  Eurobalises
  [EXTERNAL]
  to detect level transitions and certain special commands. All other messages are rejected.
- atomic: false
- implement: true
- Legal Obligation: unknown
- kind: ordinary
- ListNumberText: ·
- WordTraceId: 14564

###### 2.6.4.2.4.*[3]
Management of STM’s.
- atomic: true
- implement: true
- Legal Obligation: unknown
- kind: ordinary
- ListNumberText: ·
- WordTraceId: 14678

###### 2.6.4.2.4.*[4]
Cab signalling to the driver (depending on national system).
- implementerEnhanced: Cab signalling to the
  driver
  [EXTERNAL]
  (depending on
  national system
  [EXTERNAL]
  ).
- atomic: true
- implement: true
- Legal Obligation: unknown
- kind: ordinary
- ListNumberText: ·
- WordTraceId: 14699

#### 2.6.5
ERTMS/ETCS Application Level 1
- atomic: false
- implement: false
- Legal Obligation: not applicable
- kind: Heading
- WordTraceId: 14760

##### 2.6.5.1
General description
- atomic: false
- implement: false
- Legal Obligation: not applicable
- kind: Heading
- WordTraceId: 14791

###### 2.6.5.1.1
ERTMS/ETCS Level 1 is a spot transmission based train control system to be used as an overlay on an underlying signalling system.
- atomic: true
- implement: true
- Legal Obligation: unknown
- kind: ordinary
- WordTraceId: 14811

###### 2.6.5.1.2
Movement authorities are generated trackside and are transmitted to the train via Eurobalises.
- implementerEnhanced: Movement authorities are generated
  trackside
  [EXTERNAL]
  and are transmitted to the train via
  Eurobalises
  [EXTERNAL]
  .
- atomic: true
- implement: true
- Legal Obligation: unknown
- kind: ordinary
- WordTraceId: 14941

###### 2.6.5.1.3
ERTMS/ETCS Level 1 provides a continuous speed supervision system, which also protects against overrun of the authority.
- atomic: true
- implement: true
- Legal Obligation: unknown
- kind: ordinary
- WordTraceId: 15038

###### 2.6.5.1.4
Train detection and train integrity supervision are performed by the trackside equipment of the underlying signalling system (interlocking, track circuits etc.) and are outside the scope of ERTMS/ETCS.
- implementerEnhanced: Train detection and train integrity supervision are performed by the
  trackside
  [EXTERNAL]
  equipment of the underlying signalling system (interlocking, track circuits
  etc.
  [WEAK]
  ) and are outside the scope of ERTMS/ETCS.
- atomic: true
- implement: true
- Legal Obligation: unknown
- kind: ordinary
- WordTraceId: 15160

###### 2.6.5.1.5
Level 1 is based on Eurobalises as spot transmission devices.
- implementerEnhanced: Level 1 is based on
  Eurobalises
  [EXTERNAL]
  as spot transmission devices.
- atomic: true
- implement: true
- Legal Obligation: unknown
- kind: ordinary
- WordTraceId: 15362

###### 2.6.5.1.6
The trackside equipment does not know the train to which it sends information.
- implementerEnhanced: The
  trackside
  [EXTERNAL]
  equipment does not know the train to which it sends information.
- atomic: true
- implement: true
- Legal Obligation: unknown
- kind: ordinary
- WordTraceId: 15426

###### 2.6.5.1.7
If in level 1 a lineside signal clears, an approaching train can not receive this information until it passes the Eurobalise group at that signal. The driver therefore has to observe the lineside signal to know when to proceed. The train has then to be permitted to approach the stopping location below a maximum permitted release speed.
- implementerEnhanced: If
  [CONDITION]
  in level 1 a lineside signal clears, an approaching train can not receive this information
  until
  [TIME]
  it passes the
  Eurobalise
  [EXTERNAL]
  group at that signal. The
  driver
  [EXTERNAL]
  therefore has to observe the lineside signal to know
  when
  [CONDITION]
  to proceed. The train has then to be permitted to approach the stopping location
  below
  [WEAK]
  a maximum permitted release speed.
- atomic: false
- implement: true
- Legal Obligation: unknown
- kind: ordinary
- WordTraceId: 15505

###### 2.6.5.1.8
Additional Eurobalises can be placed between distant and main signals to transmit infill information, the train will receive new information before reaching the signal.
- implementerEnhanced: Additional
  Eurobalises
  [EXTERNAL]
  can be placed between distant and main signals to transmit infill information, the train will receive new information before reaching the signal.
- atomic: true
- implement: true
- Legal Obligation: unknown
- kind: ordinary
- WordTraceId: 15844

###### 2.6.5.1.9
Note: Lineside signals are required in level 1 applications, except if semi-continuous infill is provided.
- implementerEnhanced: Note: Lineside signals are required in level 1 applications, except
  if
  [CONDITION]
  semi-continuous infill is provided.
- atomic: false
- implement: false
- Legal Obligation: not applicable
- kind: Note
- WordTraceId: 16014

###### 2.6.5.1.10
Semi-continuous infill can be provided using Euroloop or radio in-fill. In this case, the on-board system will be able to show new information to the driver as soon as it is available and even at standstill.
- implementerEnhanced: Semi-continuous infill can be provided using
  Euroloop
  [EXTERNAL]
  or radio in-fill. In this case, the on-board system will be able to show new information to the
  driver
  [EXTERNAL]
  as soon as
  [WEAK]
  it is available and even at standstill.
- atomic: false
- implement: true
- Legal Obligation: unknown
- kind: ordinary
- WordTraceId: 16121

###### 2.6.5.1.11
Euroloop or radio in-fill can improve the safety of a level 1 system as they allow the operation without release speed.
- implementerEnhanced: Euroloop
  [EXTERNAL]
  or radio in-fill can improve the safety of a level 1 system as they allow the operation without release speed.
- atomic: true
- implement: true
- Legal Obligation: unknown
- kind: ordinary
- WordTraceId: 16330

###### 2.6.5.1.11[2]
- atomic: false
- implement: false
- Legal Obligation: not applicable
- kind: Placeholder
- WordTraceId: 16450

###### 2.6.5.1.11[2].[f]4
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- atomic: false
- implement: false
- Legal Obligation: not applicable
- kind: Figure
- WordTraceId: 16469

###### 2.6.5.1.11[2].[f]4.C
Figure {Figure 4}: ERTMS/ETCS Application Level 1 without infill function
- implementerEnhanced: Figure 4: ERTMS/ETCS Application Level 1 without infill function
- atomic: true
- implement: false
- Legal Obligation: unknown
- kind: Figure
- WordTraceId: 16469

###### 2.6.5.1.11[3]
- atomic: false
- implement: false
- Legal Obligation: not applicable
- kind: Placeholder
- WordTraceId: 16559

###### 2.6.5.1.11[3].[f]5
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- atomic: false
- implement: false
- Legal Obligation: not applicable
- kind: Figure
- WordTraceId: 16587

###### 2.6.5.1.11[3].[f]5.C
Figure {Figure 5}: ERTMS/ETCS Application Level 1 with infill function by Euroloop or Radio in-fill
- implementerEnhanced: Figure 5: ERTMS/ETCS Application Level 1 with infill function by
  Euroloop
  [EXTERNAL]
  or Radio in-fill
- atomic: true
- PlainText: Figure 5: ERTMS/ETCS Application Level 1 with infill function by Euroloop or Radio in-fill
- implement: false
- Legal Obligation: unknown
- kind: Figure
- WordTraceId: 16587

##### 2.6.5.2
Summary of characteristics of Application Level 1
- atomic: false
- implement: false
- Legal Obligation: not applicable
- kind: Heading
- WordTraceId: 16703

###### 2.6.5.2.1
Trackside equipment:
- implementerEnhanced: Trackside
  [EXTERNAL]
  equipment:
- atomic: true
- implement: false
- Legal Obligation: unknown
- kind: Heading
- WordTraceId: 16753

###### 2.6.5.2.1.*[1]
Eurobalises for spot transmission from track to train.
- implementerEnhanced: Eurobalises
  [EXTERNAL]
  for spot transmission from track to train.
- atomic: true
- implement: true
- Legal Obligation: unknown
- kind: ordinary
- ListNumberText: ·
- WordTraceId: 16775

###### 2.6.5.2.1.*[2]
Eurobalises must be able to transmit variable information.
- implementerEnhanced: Eurobalises
  [EXTERNAL]
  must be able to transmit variable information.
- atomic: true
- implement: true
- Legal Obligation: unknown
- kind: ordinary
- ListNumberText: ·
- WordTraceId: 16831

###### 2.6.5.2.1.*[3]
Semi continuous infill transmission by using Euroloop or radio in-fill is optional.
- implementerEnhanced: Semi continuous infill transmission by using
  Euroloop
  [EXTERNAL]
  or radio in-fill is optional.
- atomic: true
- implement: true
- Legal Obligation: unknown
- kind: ordinary
- ListNumberText: ·
- WordTraceId: 16890

###### 2.6.5.2.2
Main ERTMS/ETCS trackside function:
- implementerEnhanced: Main ERTMS/ETCS
  trackside
  [EXTERNAL]
  function:
- atomic: true
- implement: false
- Legal Obligation: unknown
- kind: Heading
- WordTraceId: 16974

###### 2.6.5.2.2.*[1]
Determine movement authorities according to the underlying signalling system.
- atomic: true
- implement: true
- Legal Obligation: unknown
- kind: ordinary
- ListNumberText: ·
- WordTraceId: 17010

###### 2.6.5.2.2.*[2]
Transmit movement authorities and track description data to the train.
- atomic: true
- implement: true
- Legal Obligation: unknown
- kind: ordinary
- ListNumberText: ·
- WordTraceId: 17088

###### 2.6.5.2.3
On-board equipment:
- implementerEnhanced: On-board equipment
  [SELF]
  :
- atomic: true
- implement: false
- Legal Obligation: unknown
- kind: Heading
- WordTraceId: 17161

###### 2.6.5.2.3.*[1]
Onboard equipment with Eurobalise transmission.
- implementerEnhanced: Onboard equipment
  [SELF]
  with
  Eurobalise
  [EXTERNAL]
  transmission.
- atomic: true
- implement: true
- Legal Obligation: unknown
- kind: ordinary
- ListNumberText: ·
- WordTraceId: 17181

###### 2.6.5.2.3.*[2]
Euroloop transmission if infill by Euroloop is required.
- implementerEnhanced: Euroloop
  [EXTERNAL]
  transmission
  if
  [CONDITION]
  infill by
  Euroloop
  [EXTERNAL]
  is required.
- atomic: true
- implement: true
- Legal Obligation: unknown
- kind: ordinary
- ListNumberText: ·
- WordTraceId: 17229

###### 2.6.5.2.3.*[3]
Radio in-fill transmission if infill by radio is required.
- implementerEnhanced: Radio in-fill transmission
  if
  [CONDITION]
  infill by radio is required.
- atomic: true
- implement: true
- Legal Obligation: unknown
- kind: ordinary
- ListNumberText: ·
- WordTraceId: 17286

###### 2.6.5.2.4
Main ERTMS/ETCS on-board function:
- implementerEnhanced: Main
  ERTMS/ETCS on-board
  [SELF]
  function:
- atomic: true
- implement: false
- Legal Obligation: unknown
- kind: Heading
- WordTraceId: 17345

###### 2.6.5.2.4.*[1]
Reception of movement authority and track description related to the transmitting balise.
- implementerEnhanced: Reception of movement authority and track description related to the transmitting
  balise
  [EXTERNAL]
  .
- atomic: true
- implement: true
- Legal Obligation: unknown
- kind: ordinary
- ListNumberText: ·
- WordTraceId: 17380

###### 2.6.5.2.4.*[2]
Selection of the most restrictive value of the different speeds permitted at each location ahead.
- atomic: true
- implement: true
- Legal Obligation: unknown
- kind: ordinary
- ListNumberText: ·
- WordTraceId: 17470

###### 2.6.5.2.4.*[3]
Calculation of a dynamic speed profile taking into account the train running/braking characteristics which are known on-board and the track description data.
- atomic: true
- implement: true
- Legal Obligation: unknown
- kind: ordinary
- ListNumberText: ·
- WordTraceId: 17568

###### 2.6.5.2.4.*[4]
Comparison of the actual train speed with the permitted speed and commanding of the brake application if necessary.
- implementerEnhanced: Comparison of the actual train speed with the permitted speed and commanding of the brake application
  if
  [CONDITION]
  necessary
  [WEAK]
  .
- atomic: true
- implement: true
- Legal Obligation: unknown
- kind: ordinary
- ListNumberText: ·
- WordTraceId: 17726

###### 2.6.5.2.4.*[5]
Cab signalling to the driver.
- implementerEnhanced: Cab signalling to the
  driver
  [EXTERNAL]
  .
- atomic: true
- implement: true
- Legal Obligation: unknown
- kind: ordinary
- ListNumberText: ·
- WordTraceId: 17843

#### 2.6.6
ERTMS/ETCS Application Level 2
- atomic: false
- implement: false
- Legal Obligation: not applicable
- kind: Heading
- WordTraceId: 17874

##### 2.6.6.1
General description
- atomic: false
- implement: false
- Legal Obligation: not applicable
- kind: Heading
- WordTraceId: 17905

###### 2.6.6.1.1
ERTMS/ETCS Level 2 is a radio based train control system which is used as an overlay on an underlying signalling system.
- atomic: true
- implement: true
- Legal Obligation: unknown
- kind: ordinary
- WordTraceId: 17925

###### 2.6.6.1.2
Movement authorities are generated trackside and are transmitted to the train via Euroradio.
- implementerEnhanced: Movement authorities are generated
  trackside
  [EXTERNAL]
  and are transmitted to the train via Euroradio.
- atomic: true
- implement: true
- Legal Obligation: unknown
- kind: ordinary
- WordTraceId: 18047

###### 2.6.6.1.3
ERTMS/ETCS Level 2 provides a continuous speed supervision system, which also protects against overrun of the authority.
- atomic: true
- implement: true
- Legal Obligation: unknown
- kind: ordinary
- WordTraceId: 18141

###### 2.6.6.1.4
Train detection and train integrity supervision are performed by the trackside equipment of the underlying signalling system (interlocking, track circuits etc.) and are outside the scope of ERTMS/ETCS.
- implementerEnhanced: Train detection and train integrity supervision are performed by the
  trackside
  [EXTERNAL]
  equipment of the underlying signalling system (interlocking, track circuits
  etc.
  [WEAK]
  ) and are outside the scope of ERTMS/ETCS.
- atomic: true
- implement: true
- Legal Obligation: unknown
- kind: ordinary
- WordTraceId: 18263

###### 2.6.6.1.5
Level 2 is based on Euroradio for track to train communication and on Eurobalises as spot transmission devices mainly for location referencing.
- implementerEnhanced: Level 2 is based on Euroradio for track to train communication and on
  Eurobalises
  [EXTERNAL]
  as spot transmission devices mainly for location referencing.
- atomic: true
- implement: true
- Legal Obligation: unknown
- kind: ordinary
- WordTraceId: 18465

###### 2.6.6.1.6
The trackside radio block centre which provides the information to the trains knows each ERTMS/ETCS controlled train individually by the ERTMS/ETCS identity of its leading ERTMS/ETCS on-board equipment.
- implementerEnhanced: The
  trackside
  [EXTERNAL]
  radio block centre
  [EXTERNAL]
  which provides the information to the trains knows each ERTMS/ETCS controlled train individually by the ERTMS/ETCS identity of its leading
  ERTMS/ETCS on-board equipment
  [SELF]
  .
- atomic: true
- implement: true
- Legal Obligation: unknown
- kind: ordinary
- WordTraceId: 18611

###### 2.6.6.1.7
Note: Lineside signals can be suppressed in Level 2.
- atomic: false
- implement: false
- Legal Obligation: not applicable
- kind: Note
- WordTraceId: 18815

###### 2.6.6.1.7[2]
- atomic: false
- implement: false
- Legal Obligation: not applicable
- kind: Placeholder
- WordTraceId: 18868

###### 2.6.6.1.7[2].[f]6
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- atomic: false
- implement: false
- Legal Obligation: not applicable
- kind: Figure
- WordTraceId: 18885

###### 2.6.6.1.7[2].[f]6.C
Figure {Figure 6}: ERTMS/ETCS Application Level 2
- implementerEnhanced: Figure 6: ERTMS/ETCS Application Level 2
- atomic: true
- PlainText: Figure 6: ERTMS/ETCS Application Level 2
- implement: false
- Legal Obligation: unknown
- kind: Figure
- WordTraceId: 18885

##### 2.6.6.2
Summary of characteristics of Application Level 2
- atomic: false
- implement: false
- Legal Obligation: not applicable
- kind: Heading
- WordTraceId: 18953

###### 2.6.6.2.1
Trackside equipment:
- implementerEnhanced: Trackside
  [EXTERNAL]
  equipment:
- atomic: true
- implement: false
- Legal Obligation: unknown
- kind: Heading
- WordTraceId: 19003

###### 2.6.6.2.1.*[1]
Radio block centre.
- implementerEnhanced: Radio block centre
  [EXTERNAL]
  .
- atomic: true
- implement: true
- Legal Obligation: unknown
- kind: ordinary
- ListNumberText: ·
- WordTraceId: 19025

###### 2.6.6.2.1.*[2]
Euroradio for bi-directional track-train communication.
- atomic: true
- implement: true
- Legal Obligation: unknown
- kind: ordinary
- ListNumberText: ·
- WordTraceId: 19045

###### 2.6.6.2.1.*[3]
Eurobalises mainly for location referencing.
- implementerEnhanced: Eurobalises
  [EXTERNAL]
  mainly for location referencing.
- atomic: true
- implement: true
- Legal Obligation: unknown
- kind: ordinary
- ListNumberText: ·
- WordTraceId: 19101

###### 2.6.6.2.2
Main ERTMS/ETCS trackside function:
- implementerEnhanced: Main ERTMS/ETCS
  trackside
  [EXTERNAL]
  function:
- atomic: true
- implement: false
- Legal Obligation: unknown
- kind: Heading
- WordTraceId: 19147

###### 2.6.6.2.2.*[1]
Knowing each train equipped with and running under ERTMS/ETCS within an RBC area by its ERTMS/ETCS identity.
- implementerEnhanced: Knowing each train equipped with and running under ERTMS/ETCS within an
  RBC
  [EXTERNAL]
  area by its ERTMS/ETCS identity.
- atomic: true
- implement: true
- Legal Obligation: unknown
- kind: ordinary
- ListNumberText: ·
- WordTraceId: 19183

###### 2.6.6.2.2.*[2]
Following each ERTMS/ETCS controlled train’s location within an RBC area.
- implementerEnhanced: Following each ERTMS/ETCS controlled train’s location within an
  RBC
  [EXTERNAL]
  area.
- atomic: true
- implement: true
- Legal Obligation: unknown
- kind: ordinary
- ListNumberText: ·
- WordTraceId: 19293

###### 2.6.6.2.2.*[3]
Determine movement authorities according to the underlying signalling system for each train individually.
- implementerEnhanced: Determine movement authorities according to the underlying signalling system
  for each
  [LOOP]
  train individually.
- atomic: true
- implement: true
- Legal Obligation: unknown
- kind: ordinary
- ListNumberText: ·
- WordTraceId: 19368

###### 2.6.6.2.2.*[4]
Transmit movement authorities and track description to each train individually.
- atomic: true
- implement: true
- Legal Obligation: unknown
- kind: ordinary
- ListNumberText: ·
- WordTraceId: 19474

###### 2.6.6.2.2.*[5]
Handing over of train control between different RBC’s at the RBC-RBC borders.
- atomic: true
- implement: true
- Legal Obligation: unknown
- kind: ordinary
- ListNumberText: ·
- WordTraceId: 19556

###### 2.6.6.2.3
On-board equipment:
- implementerEnhanced: On-board equipment
  [SELF]
  :
- atomic: true
- implement: false
- Legal Obligation: unknown
- kind: Heading
- WordTraceId: 19634

###### 2.6.6.2.3.*[1]
Onboard equipment with Eurobalise and Euroradio transmissions.
- implementerEnhanced: Onboard equipment
  [SELF]
  with
  Eurobalise
  [EXTERNAL]
  and Euroradio transmissions.
- atomic: true
- implement: true
- Legal Obligation: unknown
- kind: ordinary
- ListNumberText: ·
- WordTraceId: 19655

###### 2.6.6.2.4
Main ERTMS/ETCS on-board function:
- implementerEnhanced: Main
  ERTMS/ETCS on-board
  [SELF]
  function:
- atomic: true
- implement: false
- Legal Obligation: unknown
- kind: Heading
- WordTraceId: 19718

###### 2.6.6.2.4.*[1]
The train reads Eurobalises and sends its position relative to the detected balises to the radio block centre.
- implementerEnhanced: The train reads
  Eurobalises
  [EXTERNAL]
  and sends its position relative to the detected
  balises
  [EXTERNAL]
  to the
  radio block centre
  [EXTERNAL]
  .
- atomic: true
- implement: true
- Legal Obligation: unknown
- kind: ordinary
- ListNumberText: ·
- WordTraceId: 19753

###### 2.6.6.2.4.*[2]
The train receives a movement authority and the track description via Euroradio relating to a balise.
- implementerEnhanced: The train receives a movement authority and the track description via Euroradio relating to a
  balise
  [EXTERNAL]
  .
- atomic: true
- implement: true
- Legal Obligation: unknown
- kind: ordinary
- ListNumberText: ·
- WordTraceId: 19864

###### 2.6.6.2.4.*[3]
Selection of the most restrictive value of the different speeds permitted at each location ahead.
- atomic: true
- implement: true
- Legal Obligation: unknown
- kind: ordinary
- ListNumberText: ·
- WordTraceId: 19968

###### 2.6.6.2.4.*[4]
Calculation of a dynamic speed profile taking into account the train running/braking characteristics which are known on-board and the track description data.
- atomic: true
- implement: true
- Legal Obligation: unknown
- kind: ordinary
- ListNumberText: ·
- WordTraceId: 20066

###### 2.6.6.2.4.*[5]
Comparison of the actual train speed with the permitted speed and commanding of the brake application if necessary.
- implementerEnhanced: Comparison of the actual train speed with the permitted speed and commanding of the brake application
  if
  [CONDITION]
  necessary
  [WEAK]
  .
- atomic: true
- implement: true
- Legal Obligation: unknown
- kind: ordinary
- ListNumberText: ·
- WordTraceId: 20224

###### 2.6.6.2.4.*[6]
Cab signalling to the driver.
- implementerEnhanced: Cab signalling to the
  driver
  [EXTERNAL]
  .
- atomic: true
- implement: true
- Legal Obligation: unknown
- kind: ordinary
- ListNumberText: ·
- WordTraceId: 20341

#### 2.6.7
ERTMS/ETCS Application Level 3
- atomic: false
- implement: false
- Legal Obligation: not applicable
- kind: Heading
- WordTraceId: 20372

##### 2.6.7.1
General description
- atomic: false
- implement: false
- Legal Obligation: not applicable
- kind: Heading
- WordTraceId: 20403

###### 2.6.7.1.1
ERTMS/ETCS Level 3 is a radio based train control system.
- atomic: true
- implement: true
- Legal Obligation: unknown
- kind: ordinary
- WordTraceId: 20423

###### 2.6.7.1.2
Movement authorities are generated trackside and are transmitted to the train via Euroradio.
- implementerEnhanced: Movement authorities are generated
  trackside
  [EXTERNAL]
  and are transmitted to the train via Euroradio.
- atomic: true
- implement: true
- Legal Obligation: unknown
- kind: ordinary
- WordTraceId: 20481

###### 2.6.7.1.3
ERTMS/ETCS Level 3 provides a continuous speed supervision system, which also protects against overrun of the authority.
- atomic: true
- implement: true
- Legal Obligation: unknown
- kind: ordinary
- WordTraceId: 20575

###### 2.6.7.1.4
Train location and train integrity supervision are performed by the trackside radio block centre in co-operation with the train (which sends position reports and train integrity information).
- implementerEnhanced: Train location and train integrity supervision are performed by the
  trackside
  [EXTERNAL]
  radio block centre
  [EXTERNAL]
  in co-operation with the train (which sends position reports and train integrity information).
- atomic: true
- implement: true
- Legal Obligation: unknown
- kind: ordinary
- WordTraceId: 20697

###### 2.6.7.1.5
Level 3 is based on Euroradio for track to train communication and on Eurobalises as spot transmission devices mainly for location referencing.
- implementerEnhanced: Level 3 is based on Euroradio for track to train communication and on
  Eurobalises
  [EXTERNAL]
  as spot transmission devices mainly for location referencing.
- atomic: true
- implement: true
- Legal Obligation: unknown
- kind: ordinary
- WordTraceId: 20890

###### 2.6.7.1.6
The trackside radio block centre which provides the information to the trains knows each train individually by the ERTMS/ETCS identity of its leading ERTMS/ETCS on-board equipment.
- implementerEnhanced: The
  trackside
  [EXTERNAL]
  radio block centre
  [EXTERNAL]
  which provides the information to the trains knows each train individually by the ERTMS/ETCS identity of its leading
  ERTMS/ETCS on-board equipment
  [SELF]
  .
- atomic: true
- implement: true
- Legal Obligation: unknown
- kind: ordinary
- WordTraceId: 21036

###### 2.6.7.1.7
Note: Lineside signals are not foreseen to be used when operating in Level 3.
- implementerEnhanced: Note: Lineside signals are not foreseen to be used
  when
  [CONDITION]
  operating in Level 3.
- atomic: false
- implement: false
- Legal Obligation: not applicable
- kind: Note
- WordTraceId: 21218

###### 2.6.7.1.7[2]
- atomic: false
- implement: false
- Legal Obligation: not applicable
- kind: Placeholder
- WordTraceId: 21296

###### 2.6.7.1.7[2].[f]7
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- atomic: false
- implement: false
- Legal Obligation: not applicable
- kind: Figure
- WordTraceId: 21314

###### 2.6.7.1.7[2].[f]7.C
Figure {Figure 7}: ERTMS/ETCS Application Level 3
- implementerEnhanced: Figure 7: ERTMS/ETCS Application Level 3
- atomic: true
- PlainText: Figure 7: ERTMS/ETCS Application Level 3
- implement: false
- Legal Obligation: unknown
- kind: Figure
- WordTraceId: 21314

##### 2.6.7.2
Summary of characteristics of Application Level 3
- atomic: false
- implement: false
- Legal Obligation: not applicable
- kind: Heading
- WordTraceId: 21380

###### 2.6.7.2.1
Trackside equipment:
- implementerEnhanced: Trackside
  [EXTERNAL]
  equipment:
- atomic: true
- implement: false
- Legal Obligation: unknown
- kind: Heading
- WordTraceId: 21430

###### 2.6.7.2.1.*[1]
Radio block centre.
- implementerEnhanced: Radio block centre
  [EXTERNAL]
  .
- atomic: true
- implement: true
- Legal Obligation: unknown
- kind: ordinary
- ListNumberText: ·
- WordTraceId: 21452

###### 2.6.7.2.1.*[2]
Euroradio for bi-directional track-train communication.
- atomic: true
- implement: true
- Legal Obligation: unknown
- kind: ordinary
- ListNumberText: ·
- WordTraceId: 21472

###### 2.6.7.2.1.*[3]
Eurobalises for mainly location referencing.
- implementerEnhanced: Eurobalises
  [EXTERNAL]
  for mainly location referencing.
- atomic: true
- implement: true
- Legal Obligation: unknown
- kind: ordinary
- ListNumberText: ·
- WordTraceId: 21528

###### 2.6.7.2.2
Main ERTMS/ETCS trackside function:
- implementerEnhanced: Main ERTMS/ETCS
  trackside
  [EXTERNAL]
  function:
- atomic: true
- implement: false
- Legal Obligation: unknown
- kind: Heading
- WordTraceId: 21574

###### 2.6.7.2.2.*[1]
Knowing each train within an RBC area by its ERTMS/ETCS identity.
- implementerEnhanced: Knowing each train within an
  RBC
  [EXTERNAL]
  area by its ERTMS/ETCS identity.
- atomic: true
- implement: true
- Legal Obligation: unknown
- kind: ordinary
- ListNumberText: ·
- WordTraceId: 21610

###### 2.6.7.2.2.*[2]
Following each trains location within an RBC area.
- implementerEnhanced: Following each trains location within an
  RBC
  [EXTERNAL]
  area.
- atomic: true
- implement: true
- Legal Obligation: unknown
- kind: ordinary
- ListNumberText: ·
- WordTraceId: 21677

###### 2.6.7.2.2.*[3]
Route locking and route releasing based on information received from the trains.
- atomic: true
- implement: true
- Legal Obligation: unknown
- kind: ordinary
- ListNumberText: ·
- WordTraceId: 21729

###### 2.6.7.2.2.*[4]
Determine movement authorities for each train individually.
- implementerEnhanced: Determine movement authorities
  for each
  [LOOP]
  train individually.
- atomic: true
- implement: true
- Legal Obligation: unknown
- kind: ordinary
- ListNumberText: ·
- WordTraceId: 21810

###### 2.6.7.2.2.*[5]
Transmit movement authorities and track description to each train individually.
- atomic: true
- implement: true
- Legal Obligation: unknown
- kind: ordinary
- ListNumberText: ·
- WordTraceId: 21871

###### 2.6.7.2.2.*[6]
Handing over of train control between different RBC’s at the RBC-RBC borders.
- atomic: true
- implement: true
- Legal Obligation: unknown
- kind: ordinary
- ListNumberText: ·
- WordTraceId: 21953

###### 2.6.7.2.3
On-board equipment:
- implementerEnhanced: On-board equipment
  [SELF]
  :
- atomic: true
- implement: false
- Legal Obligation: unknown
- kind: Heading
- WordTraceId: 22031

###### 2.6.7.2.3.*[1]
Onboard equipment with Eurobalise and Euroradio transmissions.
- implementerEnhanced: Onboard equipment
  [SELF]
  with
  Eurobalise
  [EXTERNAL]
  and Euroradio transmissions.
- atomic: true
- implement: true
- Legal Obligation: unknown
- kind: ordinary
- ListNumberText: ·
- WordTraceId: 22052

###### 2.6.7.2.3.*[2]
Train integrity proving system.
- atomic: true
- implement: true
- Legal Obligation: unknown
- kind: ordinary
- ListNumberText: ·
- WordTraceId: 22115

###### 2.6.7.2.4
Main ERTMS/ETCS on-board functions:
- implementerEnhanced: Main
  ERTMS/ETCS on-board
  [SELF]
  functions:
- atomic: true
- implement: false
- Legal Obligation: unknown
- kind: Heading
- WordTraceId: 22147

###### 2.6.7.2.4.*[1]
The train reads Eurobalises and sends its position relative to the detected balises to the radio block centre.
- implementerEnhanced: The train reads
  Eurobalises
  [EXTERNAL]
  and sends its position relative to the detected
  balises
  [EXTERNAL]
  to the
  radio block centre
  [EXTERNAL]
  .
- atomic: true
- implement: true
- Legal Obligation: unknown
- kind: ordinary
- ListNumberText: ·
- WordTraceId: 22183

###### 2.6.7.2.4.*[2]
The train monitors train integrity (external function, not part of ERTMS/ETCS) and sends this information to the radio block centre.
- implementerEnhanced: The train monitors train integrity (
  external
  [EXTERNAL]
  function, not part of ERTMS/ETCS) and sends this information to the
  radio block centre
  [EXTERNAL]
  .
- atomic: true
- implement: true
- Legal Obligation: unknown
- kind: ordinary
- ListNumberText: ·
- WordTraceId: 22294

###### 2.6.7.2.4.*[3]
The train receives a movement authority and the track description via Euroradio relating to a balise.
- implementerEnhanced: The train receives a movement authority and the track description via Euroradio relating to a
  balise
  [EXTERNAL]
  .
- atomic: true
- implement: true
- Legal Obligation: unknown
- kind: ordinary
- ListNumberText: ·
- WordTraceId: 22427

###### 2.6.7.2.4.*[4]
Selection of the most restrictive value of the different speeds permitted at each location ahead.
- atomic: true
- implement: true
- Legal Obligation: unknown
- kind: ordinary
- ListNumberText: ·
- WordTraceId: 22531

###### 2.6.7.2.4.*[5]
Calculation of a dynamic speed profile, taking into account the train running/braking characteristics which are known on-board and the track description data.
- atomic: true
- implement: true
- Legal Obligation: unknown
- kind: ordinary
- ListNumberText: ·
- WordTraceId: 22629

###### 2.6.7.2.4.*[6]
Comparison of the actual train speed with the permitted speed and commanding of the brake application if necessary.
- implementerEnhanced: Comparison of the actual train speed with the permitted speed and commanding of the brake application
  if
  [CONDITION]
  necessary
  [WEAK]
  .
- atomic: true
- implement: true
- Legal Obligation: unknown
- kind: ordinary
- ListNumberText: ·
- WordTraceId: 22788

###### 2.6.7.2.4.*[7]
Cab signalling to the driver.
- implementerEnhanced: Cab signalling to the
  driver
  [EXTERNAL]
  .
- atomic: true
- implement: true
- Legal Obligation: unknown
- kind: ordinary
- ListNumberText: ·
- WordTraceId: 22905

#### 2.6.8
Level transitions
- atomic: false
- implement: false
- Legal Obligation: not applicable
- kind: Heading
- WordTraceId: 22936

##### 2.6.8.1
An ERTMS/ETCS equipment which is not isolated always operates in one of the above described levels. All transitions between these levels are performed according to defined functions and procedures.
- implementerEnhanced: An ERTMS/ETCS equipment which is not isolated always operates in one of the
  above
  [WEAK]
  described levels. All transitions between these levels are performed according to defined functions and procedures.
- atomic: false
- implement: true
- Legal Obligation: unknown
- kind: ordinary
- WordTraceId: 22954

##### 2.6.8.2
Additional national functions and rules which might be used by an individual railway to for example prevent not equipped trains from entering a level 2/3 area are not specified here and have to be implemented outside ERTMS/ETCS.
- implementerEnhanced: Additional national functions and rules which might be used by an individual railway to
  for example
  [WEAK]
  prevent not equipped trains from entering a level 2/3 area are not specified here and have to be implemented outside ERTMS/ETCS.
- atomic: true
- implement: true
- Legal Obligation: unknown
- kind: ordinary
- WordTraceId: 23153

##### 2.6.8.3
The following table shows all possible transitions (marked with Grey):
- atomic: true
- implement: true
- Legal Obligation: unknown
- kind: ordinary
- WordTraceId: 23382

##### 2.6.8.3[2]
- atomic: false
- implement: false
- Legal Obligation: not applicable
- kind: Placeholder
- WordTraceId: 23453

###### 2.6.8.3[2].[t]1
| [r][1].[c][1] to from | [r][1].[c][2] 0 | [r][1].[c][3] STM | [r][1].[c][4] 1 | [r][1].[c][5] 2 | [r][1].[c][6] 3 |
| --- | --- | --- | --- | --- | --- |
| [r][2].[c][1] 0 | [r][2].[c][2] | [r][2].[c][3] | [r][2].[c][4] | [r][2].[c][5] | [r][2].[c][6] |
| [r][3].[c][1] STM | [r][3].[c][2] | [r][3].[c][3] a) | [r][3].[c][4] | [r][3].[c][5] | [r][3].[c][6] |
| [r][4].[c][1] 1 | [r][4].[c][2] | [r][4].[c][3] | [r][4].[c][4] | [r][4].[c][5] | [r][4].[c][6] |
| [r][5].[c][1] 2 | [r][5].[c][2] | [r][5].[c][3] | [r][5].[c][4] | [r][5].[c][5] b) | [r][5].[c][6] |
| [r][6].[c][1] 3 | [r][6].[c][2] | [r][6].[c][3] | [r][6].[c][4] | [r][6].[c][5] | [r][6].[c][6] b) |
- atomic: false
- implement: false
- Legal Obligation: not applicable
- kind: Table
- WordTraceId: 23539

###### 2.6.8.3[2].[t]1.C
Table {Table 1}: Possible level transitions.
- implementerEnhanced: Table 1: Possible level transitions.
- atomic: true
- PlainText: Table 1: Possible level transitions.
- implement: false
- Legal Obligation: unknown
- kind: Table
- WordTraceId: 23539

###### 2.6.8.3[2].[t]1.[r][1]
- atomic: false
- implement: false
- Legal Obligation: not applicable
- kind: Table
- WordTraceId: 23453

###### 2.6.8.3[2].[t]1.[r][1].[c][1]
CONTENTS HAVE BEEN SPLIT UP - SEE CHILDREN
- atomic: false
- implement: false
- Legal Obligation: not applicable
- kind: ordinary
- WordTraceId: 23453

###### 2.6.8.3[2].[t]1.[r][1].[c][1].[1]
to
- atomic: true
- implement: true
- Legal Obligation: unknown
- kind: ordinary
- WordTraceId: 23453

###### 2.6.8.3[2].[t]1.[r][1].[c][1].[2]
from
- atomic: true
- implement: true
- Legal Obligation: unknown
- kind: ordinary
- WordTraceId: 23456

###### 2.6.8.3[2].[t]1.[r][1].[c][2]
0
- atomic: true
- implement: true
- Legal Obligation: unknown
- kind: ordinary
- WordTraceId: 23478

###### 2.6.8.3[2].[t]1.[r][1].[c][3]
STM
- atomic: true
- implement: true
- Legal Obligation: unknown
- kind: ordinary
- WordTraceId: 23480

###### 2.6.8.3[2].[t]1.[r][1].[c][4]
1
- atomic: true
- implement: true
- Legal Obligation: unknown
- kind: ordinary
- WordTraceId: 23484

###### 2.6.8.3[2].[t]1.[r][1].[c][5]
2
- atomic: true
- implement: true
- Legal Obligation: unknown
- kind: ordinary
- WordTraceId: 23486

###### 2.6.8.3[2].[t]1.[r][1].[c][6]
3
- atomic: true
- implement: true
- Legal Obligation: unknown
- kind: ordinary
- WordTraceId: 23488

###### 2.6.8.3[2].[t]1.[r][2]
- atomic: false
- implement: false
- Legal Obligation: not applicable
- kind: Table
- WordTraceId: 23491

###### 2.6.8.3[2].[t]1.[r][2].[c][1]
0
- atomic: true
- implement: true
- Legal Obligation: unknown
- kind: ordinary
- WordTraceId: 23491

###### 2.6.8.3[2].[t]1.[r][2].[c][2]
- atomic: true
- implement: true
- Legal Obligation: unknown
- kind: ordinary
- WordTraceId: 23493

###### 2.6.8.3[2].[t]1.[r][2].[c][3]
- atomic: true
- implement: true
- Legal Obligation: unknown
- kind: ordinary
- WordTraceId: 23494

###### 2.6.8.3[2].[t]1.[r][2].[c][4]
- atomic: true
- implement: true
- Legal Obligation: unknown
- kind: ordinary
- WordTraceId: 23495

###### 2.6.8.3[2].[t]1.[r][2].[c][5]
- atomic: true
- implement: true
- Legal Obligation: unknown
- kind: ordinary
- WordTraceId: 23496

###### 2.6.8.3[2].[t]1.[r][2].[c][6]
- atomic: true
- implement: true
- Legal Obligation: unknown
- kind: ordinary
- WordTraceId: 23497

###### 2.6.8.3[2].[t]1.[r][3]
- atomic: false
- implement: false
- Legal Obligation: not applicable
- kind: Table
- WordTraceId: 23499

###### 2.6.8.3[2].[t]1.[r][3].[c][1]
STM
- atomic: true
- implement: true
- Legal Obligation: unknown
- kind: ordinary
- WordTraceId: 23499

###### 2.6.8.3[2].[t]1.[r][3].[c][2]
- atomic: true
- implement: true
- Legal Obligation: unknown
- kind: ordinary
- WordTraceId: 23503

###### 2.6.8.3[2].[t]1.[r][3].[c][3]
a)
- atomic: true
- implement: true
- Legal Obligation: unknown
- kind: ordinary
- WordTraceId: 23504

###### 2.6.8.3[2].[t]1.[r][3].[c][4]
- atomic: true
- implement: true
- Legal Obligation: unknown
- kind: ordinary
- WordTraceId: 23507

###### 2.6.8.3[2].[t]1.[r][3].[c][5]
- atomic: true
- implement: true
- Legal Obligation: unknown
- kind: ordinary
- WordTraceId: 23508

###### 2.6.8.3[2].[t]1.[r][3].[c][6]
- atomic: true
- implement: true
- Legal Obligation: unknown
- kind: ordinary
- WordTraceId: 23509

###### 2.6.8.3[2].[t]1.[r][4]
- atomic: false
- implement: false
- Legal Obligation: not applicable
- kind: Table
- WordTraceId: 23511

###### 2.6.8.3[2].[t]1.[r][4].[c][1]
1
- atomic: true
- implement: true
- Legal Obligation: unknown
- kind: ordinary
- WordTraceId: 23511

###### 2.6.8.3[2].[t]1.[r][4].[c][2]
- atomic: true
- implement: true
- Legal Obligation: unknown
- kind: ordinary
- WordTraceId: 23513

###### 2.6.8.3[2].[t]1.[r][4].[c][3]
- atomic: true
- implement: true
- Legal Obligation: unknown
- kind: ordinary
- WordTraceId: 23514

###### 2.6.8.3[2].[t]1.[r][4].[c][4]
- atomic: true
- implement: true
- Legal Obligation: unknown
- kind: ordinary
- WordTraceId: 23515

###### 2.6.8.3[2].[t]1.[r][4].[c][5]
- atomic: true
- implement: true
- Legal Obligation: unknown
- kind: ordinary
- WordTraceId: 23516

###### 2.6.8.3[2].[t]1.[r][4].[c][6]
- atomic: true
- implement: true
- Legal Obligation: unknown
- kind: ordinary
- WordTraceId: 23517

###### 2.6.8.3[2].[t]1.[r][5]
- atomic: false
- implement: false
- Legal Obligation: not applicable
- kind: Table
- WordTraceId: 23519

###### 2.6.8.3[2].[t]1.[r][5].[c][1]
2
- atomic: true
- implement: true
- Legal Obligation: unknown
- kind: ordinary
- WordTraceId: 23519

###### 2.6.8.3[2].[t]1.[r][5].[c][2]
- atomic: true
- implement: true
- Legal Obligation: unknown
- kind: ordinary
- WordTraceId: 23521

###### 2.6.8.3[2].[t]1.[r][5].[c][3]
- atomic: true
- implement: true
- Legal Obligation: unknown
- kind: ordinary
- WordTraceId: 23522

###### 2.6.8.3[2].[t]1.[r][5].[c][4]
- atomic: true
- implement: true
- Legal Obligation: unknown
- kind: ordinary
- WordTraceId: 23523

###### 2.6.8.3[2].[t]1.[r][5].[c][5]
b)
- atomic: true
- implement: true
- Legal Obligation: unknown
- kind: ordinary
- WordTraceId: 23524

###### 2.6.8.3[2].[t]1.[r][5].[c][6]
- atomic: true
- implement: true
- Legal Obligation: unknown
- kind: ordinary
- WordTraceId: 23527

###### 2.6.8.3[2].[t]1.[r][6]
- atomic: false
- implement: false
- Legal Obligation: not applicable
- kind: Table
- WordTraceId: 23529

###### 2.6.8.3[2].[t]1.[r][6].[c][1]
3
- atomic: true
- implement: true
- Legal Obligation: unknown
- kind: ordinary
- WordTraceId: 23529

###### 2.6.8.3[2].[t]1.[r][6].[c][2]
- atomic: true
- implement: true
- Legal Obligation: unknown
- kind: ordinary
- WordTraceId: 23531

###### 2.6.8.3[2].[t]1.[r][6].[c][3]
- atomic: true
- implement: true
- Legal Obligation: unknown
- kind: ordinary
- WordTraceId: 23532

###### 2.6.8.3[2].[t]1.[r][6].[c][4]
- atomic: true
- implement: true
- Legal Obligation: unknown
- kind: ordinary
- WordTraceId: 23533

###### 2.6.8.3[2].[t]1.[r][6].[c][5]
- atomic: true
- implement: true
- Legal Obligation: unknown
- kind: ordinary
- WordTraceId: 23534

###### 2.6.8.3[2].[t]1.[r][6].[c][6]
b)
- atomic: true
- implement: true
- Legal Obligation: unknown
- kind: ordinary
- WordTraceId: 23535

###### 2.6.8.3[2].a
Transitions between level STM and level STM describe the switching from one STM to another STM.
- atomic: true
- implement: true
- Legal Obligation: unknown
- kind: ordinary
- ListNumberText: a)
- WordTraceId: 23600

###### 2.6.8.3[2].b
Transitions between level 2 and level 2 respectively between level 3 and level 3 describe the handover between RBC’s.
- atomic: true
- implement: true
- Legal Obligation: unknown
- kind: ordinary
- ListNumberText: b)
- WordTraceId: 23697
