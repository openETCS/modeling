# Subset026

# Specification: Specification Document
- Description: Subset026

## 1
System Requirements Specification Chapter 1 Introduction
- kind: Heading
- WordTraceId: 26
- implement: false
- Legal Obligation: unknown
- atomic: true

### 1.1
Modification History
- kind: ordinary
- WordTraceId: 282
- implement: true
- Legal Obligation: not applicable
- atomic: false

### 1.1[2]
- kind: Placeholder
- WordTraceId: 303
- implement: false
- Legal Obligation: not applicable
- atomic: false

#### 1.1[2].[t]*
| Issue Number Date | Section Number | Modification / Description | Author / Editor |
| --- | --- | --- | --- |
| 0.0.1 | All | first issue | SAB |
| 0.1.0 | All | Review comments from Adtranz | SAB |
| 1.0.0 | All | Final review | SAB |
| 1.0.2 / 15. Apr. 1999 | All | Reworked edition | SAB |
| 1.0.3 / 22. Apr. 1999 | 1.8.9 | Comment of Alstom | SAB |
| 1.1.0 / 23. Apr. 1999 |  | Final issue of class P SRS | Ch. Frerichs (ed.) |
| 1.1.1 / 27. Mai 1999 | 1.3.1.1/1.7.1.2 | Review comments added | SAB |
| 1.1.2 |  | Draft for class 1 | SAB |
| 1.1.3 990729 | Document reference number. | Revision during finalisation meeting, Stuttgart 990729 | HE |
| 1.2.0 990730 | Version number | Release version | HE |
| 1.2.1 991209 | All | First draft for 2 nd release | SAB |
| 1.3.0 991216 | All | Review comments added | SAB |
| 2.0.0 991222 | Minor editing | Finalisation | SAB |
| 2.0.1 | All | Corrections after review | SAB |
| 2.1.0 | Version number | UNISIG release | SAB |
| 2.2.0 | Version number | UNISIG release | SAB |
| 2.2.2 1.2.2002 | Version number | Final edition | Ch. Frerichs |
| 2.3.0 24/02/06 | Version number, no change since 2.2.2 | Release version | HK |
- kind: Table
- WordTraceId: 1285
- implement: false
- Legal Obligation: not applicable
- atomic: false

### 1.2
Table of Contents
- kind: ordinary
- WordTraceId: 1286
- implement: true
- Legal Obligation: not applicable
- atomic: false

### 1.3
Introduction
- kind: Heading
- WordTraceId: 2296
- implement: false
- Legal Obligation: not applicable
- atomic: false

#### 1.3.1
PLACEHOLDER REQUIREMENT - DO NOT TRACE
- kind: Placeholder
- WordTraceId: 2309
- implement: false
- Legal Obligation: not applicable
- atomic: false

##### 1.3.1.1
Train control is an important part of any railway operations management system. In the past a number of different Automatic Train Control (ATC) systems have evolved in different countries at different times. These systems are incompatible and not interoperable with each other. Only a few of these systems are used in more than one country, and even in those cases there have been differences in detailed development which have resulted in incompatible and not interoperable versions.
- kind: ordinary
- WordTraceId: 2309
- implement: true
- Legal Obligation: unknown
- atomic: false

##### 1.3.1.2
Many railways anticipate a significant increase in density of train traffic and are rethinking their infrastructure strategy, to accommodate high levels of traffic, in which ATC systems play an important part. Also many railways would like to introduce standardised systems to reduce system costs. In order to establish international standardisation of ATC systems, the following document specifies the European Rail Traffic Management System/European Train Control System (ERTMS/ETCS).
- implementerEnhanced: Many railways anticipate a
  significant
  [WEAK]
  increase in density of train traffic and are rethinking their infrastructure strategy, to accommodate high levels of traffic, in which ATC systems play an important part. Also many railways would like to introduce standardised systems to reduce system costs. In order to establish international standardisation of ATC systems, the following document specifies the European Rail Traffic Management System/European Train Control System (ERTMS/ETCS).
- kind: ordinary
- WordTraceId: 2794
- implement: true
- Legal Obligation: unknown
- atomic: false

### 1.4
Advantages of an International Interoperable System
- kind: Heading
- WordTraceId: 3281
- implement: false
- Legal Obligation: not applicable
- atomic: false

#### 1.4.1
PLACEHOLDER REQUIREMENT - DO NOT TRACE
- kind: Placeholder
- WordTraceId: 3333
- implement: false
- Legal Obligation: not applicable
- atomic: false

##### 1.4.1.1
The advantages expected by the railways can be summarised as:
- kind: Heading
- WordTraceId: 3333
- implement: false
- Legal Obligation: unknown
- atomic: true

###### 1.4.1.1.*[1]
Cross border interoperability.
- ListNumberText: ·
- kind: ordinary
- WordTraceId: 3395
- implement: true
- Legal Obligation: unknown
- atomic: true

###### 1.4.1.1.*[2]
Improvement of the safety of national and international train traffic.
- ListNumberText: ·
- kind: ordinary
- WordTraceId: 3426
- implement: true
- Legal Obligation: unknown
- atomic: true

###### 1.4.1.1.*[3]
Improvement of international passengers and freight train traffic management.
- ListNumberText: ·
- kind: ordinary
- WordTraceId: 3497
- implement: true
- Legal Obligation: unknown
- atomic: true

###### 1.4.1.1.*[4]
Shorter headway on heavily trafficked lines, by driving on moving block, enabling exploitation of maximum track capacity.
- ListNumberText: ·
- kind: ordinary
- WordTraceId: 3576
- implement: true
- Legal Obligation: unknown
- atomic: true

###### 1.4.1.1.*[5]
The possibility of step-by-step introduction of the new technology.
- ListNumberText: ·
- kind: ordinary
- WordTraceId: 3698
- implement: true
- Legal Obligation: unknown
- atomic: true

###### 1.4.1.1.*[6]
Enabling Pan-European competition between the manufacturers of ERTMS/ETCS components. Strengthening the position of the European railway industry on the world market.
- ListNumberText: ·
- kind: ordinary
- WordTraceId: 3766
- implement: true
- Legal Obligation: unknown
- atomic: false

###### 1.4.1.1.*[7]
Enabling preconditions for future harmonisation in other areas of rail traffic management.
- ListNumberText: ·
- kind: ordinary
- WordTraceId: 3933
- implement: true
- Legal Obligation: unknown
- atomic: true

### 1.5
About this Document
- kind: Heading
- WordTraceId: 4024
- implement: false
- Legal Obligation: not applicable
- atomic: false

#### 1.5.1
PLACEHOLDER REQUIREMENT - DO NOT TRACE
- kind: Placeholder
- WordTraceId: 4044
- implement: false
- Legal Obligation: not applicable
- atomic: false

##### 1.5.1.1
The purpose of this document is to specify the future unified standard European Train Control System ETCS from a technical point of view.
- kind: ordinary
- WordTraceId: 4044
- implement: true
- Legal Obligation: unknown
- atomic: true

##### 1.5.1.2
Some parts of the system are only specified to allow a migration from existing train control systems to ETCS (e.g. STM’s) over a transition period. They might be removed in a future edition of the standard.
- implementerEnhanced: Some parts of the system are only specified to allow a migration from existing train control systems to ETCS (
  e.g.
  [WEAK]
  STM’s) over a transition period. They might be removed in a future edition of the standard.
- kind: ordinary
- WordTraceId: 4182
- implement: true
- Legal Obligation: unknown
- atomic: false

##### 1.5.1.3
To reach technical interoperability it is necessary not only that telegrams are generated and understood according to well specified rules but also that a train respectively trackside equipment reacts in a uniform way to information received. Technical interoperability requires specifications of a detailed level.
- implementerEnhanced: To reach technical interoperability it is necessary not only that telegrams are generated and understood according to well specified rules but also that a train respectively
  trackside
  [EXTERNAL]
  equipment reacts in a uniform way to information received. Technical interoperability requires specifications of a detailed level.
- kind: ordinary
- WordTraceId: 4389
- implement: true
- Legal Obligation: unknown
- atomic: false

##### 1.5.1.4
For operational interoperability it is necessary to add operating rules, engineering standards etc. to the system design. Reaching operational interoperability is outside the scope of the SRS.
- implementerEnhanced: For operational interoperability it is necessary to add operating rules, engineering standards
  etc.
  [WEAK]
  to the system design. Reaching operational interoperability is outside the scope of the SRS.
- kind: ordinary
- WordTraceId: 4705
- implement: true
- Legal Obligation: unknown
- atomic: false

### 1.6
How to Read and Use the SRS
- kind: Heading
- WordTraceId: 4899
- implement: false
- Legal Obligation: not applicable
- atomic: false

#### 1.6.1
PLACEHOLDER REQUIREMENT - DO NOT TRACE
- kind: Placeholder
- WordTraceId: 4928
- implement: false
- Legal Obligation: not applicable
- atomic: false

##### 1.6.1.1
The SRS covers 7 chapters, which are briefly described in the section following this introduction.
- kind: ordinary
- WordTraceId: 4928
- implement: true
- Legal Obligation: unknown
- atomic: true

##### 1.6.1.2
All readers may need to refer to the UNISIG Glossary.
- kind: ordinary
- WordTraceId: 5027
- implement: true
- Legal Obligation: optional
- atomic: true

### 1.7
Mandatory and Optional Requirements
- kind: Heading
- WordTraceId: 5081
- implement: false
- Legal Obligation: not applicable
- atomic: false

#### 1.7.1
PLACEHOLDER REQUIREMENT - DO NOT TRACE
- kind: Placeholder
- WordTraceId: 5118
- implement: false
- Legal Obligation: not applicable
- atomic: false

##### 1.7.1.1
This specification often offers multiple solutions on how to implement a specific function. It therefore contains both mandatory and optional requirements. Mandatory requirements are always referred to using the word “shall” where else optional requirements are referred to using the word “may”.
- kind: ordinary
- WordTraceId: 5118
- implement: true
- Legal Obligation: unknown
- atomic: false

##### 1.7.1.2
The fact that this specification indicates a mandatory solution for the implementation of a function does not generally require that the function is implemented on a specific line but only that if the function is implemented it shall be done in the specified way. Trains will have to handle all mandatory functions as it is decided trackside whether to use them or not.
- implementerEnhanced: The fact that this specification indicates a mandatory solution for the implementation of a function does not
  generally
  [WEAK]
  require that the function is implemented on a specific line but only that
  if
  [CONDITION]
  the function is implemented it shall be done in the specified way. Trains will have to handle all mandatory functions as it is decided
  trackside
  [EXTERNAL]
  whether
  [CONDITION]
  to use them or not.
- kind: ordinary
- WordTraceId: 5415
- implement: true
- Legal Obligation: mandatory
- atomic: false

##### 1.7.1.3
Some parts of the specifications are depending on how ETCS is implemented (e.g., level). Corresponding functionality shall be mandatory or not on-board, according to the trackside implementation. It is not the scope of this specification to mandate a specific use of ETCS.
- implementerEnhanced: Some parts of the specifications are depending on how ETCS is implemented (
  e.g.
  [WEAK]
  , level). Corresponding functionality shall be mandatory or not on-board, according to the
  trackside
  [EXTERNAL]
  implementation. It is not the scope of this specification to mandate a specific use of ETCS.
- kind: ordinary
- WordTraceId: 5785
- implement: true
- Legal Obligation: mandatory
- atomic: true

##### 1.7.1.4
Notes are added to the specification in some parts for clarification. They however never contain requirements.
- kind: ordinary
- WordTraceId: 6060
- implement: true
- Legal Obligation: unknown
- atomic: false

##### 1.7.1.5
Not specified requirements and solutions are only permitted as long as they do not generate any interoperability problems.
- implementerEnhanced: Not specified requirements and solutions are only permitted
  as long as
  [TIME]
  they do not generate any interoperability problems.
- kind: ordinary
- WordTraceId: 6171
- implement: true
- Legal Obligation: unknown
- atomic: true

### 1.8
Contents of the SRS
- kind: Heading
- WordTraceId: 6297
- implement: false
- Legal Obligation: not applicable
- atomic: false

#### 1.8.1
PLACEHOLDER REQUIREMENT - DO NOT TRACE
- kind: Placeholder
- WordTraceId: 6317
- implement: false
- Legal Obligation: not applicable
- atomic: false

##### 1.8.1.1
The SRS defines the system requirements for the European Train Control System (ETCS) of ERTMS. It is the translation of the mandatory functional requirements defined by the Functional Requirements Specification (UIC/A200 FRS version 4.3, in the following chapters refered to as “FRS”) into a technical specification for developers.
- kind: Definition
- WordTraceId: 6317
- implement: false
- Legal Obligation: unknown
- atomic: false

##### 1.8.1.2
This sub-section is intended to give a rough overview of the contents of each chapter within the SRS so that readers interested only in specialised subjects can easily find the relevant chapters.
- implementerEnhanced: This sub-section is intended to give a
  rough
  [WEAK]
  overview of the contents of each chapter within the SRS so that readers interested only in specialised subjects can easily find the relevant chapters.
- kind: ordinary
- WordTraceId: 6650
- implement: true
- Legal Obligation: unknown
- atomic: true

#### 1.8.2
Chapter 1: Introduction
- kind: Heading
- WordTraceId: 6846
- implement: false
- Legal Obligation: not applicable
- atomic: false

##### 1.8.2.1
Chapter 1 (this chapter) gives a general introduction to the intention and structure of the SRS, including a brief overview of the contents of each chapter.
- kind: ordinary
- WordTraceId: 6870
- implement: true
- Legal Obligation: unknown
- atomic: true

#### 1.8.3
Chapter 2: Basic System Description
- kind: Heading
- WordTraceId: 7027
- implement: false
- Legal Obligation: not applicable
- atomic: false

##### 1.8.3.1
Chapter 2 gives an overview of the ERTMS/ETCS system structure.
- kind: ordinary
- WordTraceId: 7063
- implement: true
- Legal Obligation: unknown
- atomic: true

##### 1.8.3.2
Chapter 2 also contains a description of the basic application levels.
- kind: ordinary
- WordTraceId: 7127
- implement: true
- Legal Obligation: unknown
- atomic: true

##### 1.8.3.3
Chapter 2 does not contain technical requirements.
- kind: ordinary
- WordTraceId: 7199
- implement: true
- Legal Obligation: unknown
- atomic: true

#### 1.8.4
Chapter 3: Principles
- kind: Heading
- WordTraceId: 7251
- implement: false
- Legal Obligation: not applicable
- atomic: false

##### 1.8.4.1
Chapter 3 specifies the system principles of ETCS/ERTMS. These principles apply to onboard and trackside subsystems.
- implementerEnhanced: Chapter 3 specifies the system principles of ETCS/ERTMS. These principles apply to onboard and
  trackside
  [EXTERNAL]
  subsystems.
- kind: ordinary
- WordTraceId: 7273
- implement: true
- Legal Obligation: unknown
- atomic: false

##### 1.8.4.2
The principles define the behaviour of the system in general and functional terms.
- kind: ordinary
- WordTraceId: 7391
- implement: true
- Legal Obligation: unknown
- atomic: true

#### 1.8.5
Chapter 4: Modes and Transitions
- kind: Heading
- WordTraceId: 7475
- implement: false
- Legal Obligation: not applicable
- atomic: false

##### 1.8.5.1
PLACEHOLDER REQUIREMENT - DO NOT TRACE
- kind: Placeholder
- WordTraceId: 7508
- implement: false
- Legal Obligation: not applicable
- atomic: false

###### 1.8.5.1.1
Chapter 4 defines the modes of the ERTMS/ETCS onboard equipment and all transitions between modes.
- implementerEnhanced: Chapter 4 defines the modes of the
  ERTMS/ETCS onboard equipment
  [SELF]
  and all transitions between modes.
- kind: Definition
- WordTraceId: 7508
- implement: false
- Legal Obligation: unknown
- atomic: true

#### 1.8.6
Chapter 5: Procedures
- kind: Heading
- WordTraceId: 7607
- implement: false
- Legal Obligation: not applicable
- atomic: false

##### 1.8.6.1
Chapter 5 defines the dynamic behaviour of procedures that are necessary for interoperability. Procedures are presented by a state transition chart and a corresponding table, where all elements (States, events, transitions) of the chart are defined. The description of the procedures shows all states of the ERTMS/ETCS onboard unit and the conditions that must be fulfilled to switch from one state to another.
- implementerEnhanced: Chapter 5 defines the dynamic behaviour of procedures that are necessary for interoperability. Procedures are presented by a state transition chart and a corresponding table, where all elements (States, events, transitions) of the chart are defined. The description of the procedures shows all states of the
  ERTMS/ETCS onboard
  [SELF]
  unit and the conditions that must be fulfilled to switch from one state to another.
- kind: Definition
- WordTraceId: 7629
- implement: false
- Legal Obligation: unknown
- atomic: false

#### 1.8.7
Chapter 6: Intentionally deleted
- kind: ordinary
- WordTraceId: 8040
- implement: true
- Legal Obligation: not applicable
- atomic: false

#### 1.8.8
Chapter 7: ERTMS/ETCS Language
- kind: Heading
- WordTraceId: 8074
- implement: false
- Legal Obligation: not applicable
- atomic: false

##### 1.8.8.1
Chapter 7 defines and describes the necessary variables to be used for the data flow over the air gap between track and train. The grouping of these into packets is described. The format of messages is given in Chapter 8.
- kind: Definition
- WordTraceId: 8105
- implement: false
- Legal Obligation: unknown
- atomic: false

#### 1.8.9
Chapter 8: Messages
- kind: Heading
- WordTraceId: 8327
- implement: false
- Legal Obligation: not applicable
- atomic: false

##### 1.8.9.1
Chapter 8 defines the application protocol (format and content of messages, logical sequence for radio) necessary to achieve technical interoperability.
- kind: Definition
- WordTraceId: 8347
- implement: false
- Legal Obligation: unknown
- atomic: true

##### 1.8.9.2
The scope of this chapter is limited to the application protocol and the content of messages.
- kind: ordinary
- WordTraceId: 8500
- implement: true
- Legal Obligation: unknown
- atomic: true
